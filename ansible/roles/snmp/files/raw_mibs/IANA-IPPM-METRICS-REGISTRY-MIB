IANA-IPPM-METRICS-REGISTRY-MIB DEFINITIONS ::= BEGIN

IMPORTS

    OBJECT-IDENTITY, MODULE-IDENTITY, mib-2
        FROM SNMPv2-SMI;

ianaIppmMetricsRegistry MODULE-IDENTITY
LAST-UPDATED "200507280000Z"    -- July 28, 2005
ORGANIZATION "IANA"
CONTACT-INFO "Internet Assigned Numbers Authority

         Postal: ICANN
             4676 Admiralty Way, Suite 330
             Marina del Rey, CA 90292

         Tel:    +1 310 823 9358
         E-Mail: iana@iana.org"
DESCRIPTION
   "This module defines a registry for IP Performance Metrics.

   Registrations are done sequentially by IANA in the ianaIppmMetrics
   subtree on the basis of 'Specification Required', as defined in
   [RFC2434].

   The reference of the specification must point to a stable document
   including a title, a revision, and a date.

   The name always starts with the name of the organization and must
   respect the SMIv2 rules for descriptors defined in section 3.1 of
   [RFC2578].

   A document that creates new metrics would have an IANA
   considerations section in which it would describe new metrics to
   be registered.

   An OBJECT IDENTITY assigned to a metric is definitive and cannot
   be reused.  If a new version of a metric is produced, then it is
   assigned with a new name and a new identifier.

   Copyright (C) The Internet Society (2005).  The initial version of
   this MIB module was published in RFC 4148; for full legal notices
   see the RFC itself or
   http://www.ietf.org/copyrights/ianamib.html."

REVISION      "200507280000Z"    -- July 28, 2005
DESCRIPTION
    "Initial version of the IPPM metrics registry module.
     This version published as RFC 4148."
::= { mib-2 128 }

ianaIppmMetrics OBJECT-IDENTITY
    STATUS       current
    DESCRIPTION
        "Registration point for IP Performance Metrics."
    ::= { ianaIppmMetricsRegistry 1 }

--
-- Registry of the metrics of the IPPM WG RFCs
--

--
-- RFC 2678 "IPPM Metrics for Measuring Connectivity"
--

ietfInstantUnidirConnectivity OBJECT-IDENTITY
    STATUS     current
    DESCRIPTION
        "Type-P-Instantaneous-Unidirectional-Connectivity"
    REFERENCE "RFC2678, section 2."
    ::= { ianaIppmMetrics 1}

ietfInstantBidirConnectivity OBJECT-IDENTITY
    STATUS     current
    DESCRIPTION
        "Type-P-Instantaneous-Bidirectional-Connectivity"
    REFERENCE "RFC2678, section 3."
    ::= { ianaIppmMetrics 2}

ietfIntervalUnidirConnectivity OBJECT-IDENTITY
    STATUS     current
    DESCRIPTION
        "Type-P-Interval-Unidirectional-Connectivity"
    REFERENCE "RFC2678, section 4."
    ::= { ianaIppmMetrics 3 }

ietfIntervalBidirConnectivity OBJECT-IDENTITY
    STATUS current
    DESCRIPTION
        "Type-P-Interval-Bidirectional-Connectivity"
    REFERENCE "RFC2678, section 5."
    ::= { ianaIppmMetrics 4 }

ietfIntervalTemporalConnectivity OBJECT-IDENTITY
    STATUS     current
    DESCRIPTION
        "Type-P1-P2-Interval-Temporal-Connectivity"
    REFERENCE "RFC2678, section 6."
    ::= { ianaIppmMetrics 5 }

--
-- RFC 2679 "A One-way Delay Metric for IPPM"
--

ietfOneWayDelay OBJECT-IDENTITY
    STATUS     current
    DESCRIPTION
        "Type-P-One-way-Delay"
    REFERENCE "RFC2679, section 3."
    ::= { ianaIppmMetrics 6 }

ietfOneWayDelayPoissonStream OBJECT-IDENTITY
    STATUS     current
    DESCRIPTION
        "Type-P-One-way-Delay-Poisson-Stream"
    REFERENCE "RFC2679, section 4."
    ::= { ianaIppmMetrics 7 }

ietfOneWayDelayPercentile OBJECT-IDENTITY
    STATUS     current
    DESCRIPTION
        "Type-P-One-way-Delay-Percentile"
    REFERENCE "RFC2679, section 5.1."
    ::= { ianaIppmMetrics 8 }

ietfOneWayDelayMedian OBJECT-IDENTITY
    STATUS     current
    DESCRIPTION
        "Type-P-One-way-Delay-Median"
    REFERENCE "RFC2679, section 5.2."
    ::= { ianaIppmMetrics 9 }

ietfOneWayDelayMinimum OBJECT-IDENTITY
    STATUS     current
    DESCRIPTION
        "Type-P-One-way-Delay-Minimum"
    REFERENCE "RFC2679, section 5.3."
    ::= { ianaIppmMetrics 10 }

ietfOneWayDelayInversePercentile OBJECT-IDENTITY
    STATUS     current
    DESCRIPTION
        "Type-P-One-way-Delay-Inverse-Percentile"
    REFERENCE "RFC2679, section 5.4."
    ::= { ianaIppmMetrics 11 }

--
-- RFC 2680 "One-way Packet Loss Metric for IPPM"
--

ietfOneWayPktLoss OBJECT-IDENTITY
    STATUS     current
    DESCRIPTION
        "Type-P-One-way-Packet-Loss"
    REFERENCE "RFC2680, section 2."
    ::= { ianaIppmMetrics 12 }

ietfOneWayPktLossPoissonStream OBJECT-IDENTITY
    STATUS     current
    DESCRIPTION
        "Type-P-One-way-Packet-Loss-Poisson-Stream"
    REFERENCE "RFC2680, section 3."
    ::= { ianaIppmMetrics 13 }

ietfOneWayPktLossAverage OBJECT-IDENTITY
    STATUS     current
    DESCRIPTION
        "Type-P-One-way-Packet-Loss-Average"
    REFERENCE "RFC2680, section 4."
    ::= { ianaIppmMetrics 14 }

--
-- RFC 2681 "A Round-trip Delay Metric for IPPM"
--

ietfRoundTripDelay OBJECT-IDENTITY
    STATUS     current
    DESCRIPTION
        "Type-P-Round-trip-Delay"
    REFERENCE " section 2 of the rfc2681."
    ::= { ianaIppmMetrics 15 }

ietfRoundTripDelayPoissonStream OBJECT-IDENTITY
    STATUS     current
    DESCRIPTION
        "Type-P-Round-trip-Delay-Poisson-Stream"
    REFERENCE "RFC2681, section 4."
    ::= { ianaIppmMetrics 16 }

ietfRoundTripDelayPercentile OBJECT-IDENTITY
    STATUS     current
    DESCRIPTION
        "Type-P-Round-trip-Delay-Percentile"
    REFERENCE "RFC2681, section 4.1."
    ::= { ianaIppmMetrics 17 }

ietfRoundTripDelayMedian OBJECT-IDENTITY
    STATUS     current
    DESCRIPTION
        "Type-P-Round-trip-Delay-Median"
    REFERENCE "RFC2681, section 4.2."
    ::= { ianaIppmMetrics 18 }

ietfRoundTripDelayMinimum OBJECT-IDENTITY
    STATUS     current
    DESCRIPTION
        "Type-P-Round-trip-Delay-Minimum"
    REFERENCE "RFC2681, section 4.3."
    ::= { ianaIppmMetrics 19 }

ietfRoundTripDelayInvPercentile OBJECT-IDENTITY
    STATUS     current
    DESCRIPTION
        "Type-P-Round-trip-Inverse-Percentile"
    REFERENCE "RFC2681, section 4.4."
    ::= { ianaIppmMetrics 20 }

--
-- RFC 3357: "One-way Loss Pattern Sample Metrics"
--

ietfOneWayLossDistanceStream OBJECT-IDENTITY
    STATUS     current
    DESCRIPTION
        "Type-P-One-Way-Loss-Distance-Stream"
    REFERENCE " RFC3357, section 5.4.1."
    ::={ ianaIppmMetrics 21}

ietfOneWayLossPeriodStream OBJECT-IDENTITY
    STATUS     current
    DESCRIPTION
        "Type-P-One-Way-Loss-Period-Stream"
    REFERENCE " RFC3357, section 5.4.2."
    ::={ ianaIppmMetrics 22}

ietfOneWayLossNoticeableRate OBJECT-IDENTITY
    STATUS     current
    DESCRIPTION
        "Type-P-One-Way-Loss-Noticeable-Rate"
    REFERENCE " RFC3357, section 6.1."
    ::= { ianaIppmMetrics 23 }

ietfOneWayLossPeriodTotal OBJECT-IDENTITY
    STATUS     current
    DESCRIPTION
        "Type-P-One-Way-Loss-Period-Total"
    REFERENCE " RFC3357, section 6.2."
    ::= { ianaIppmMetrics 24 }

ietfOneWayLossPeriodLengths OBJECT-IDENTITY
    STATUS     current
    DESCRIPTION
        "Type-P-One-Way-Loss-Period-Lengths"
    REFERENCE " RFC3357, section 6.3."
    ::= { ianaIppmMetrics 25 }

ietfOneWayInterLossPeriodLengths OBJECT-IDENTITY
    STATUS     current
    DESCRIPTION
        "Type-P-One-Way-Inter-Loss-Period-Lengths"
    REFERENCE " RFC3357, section 6.4."
    ::= { ianaIppmMetrics 26 }

--
-- RFC 3393: "IP Packet Delay Variation Metric
--           for IP Performance Metrics (IPPM)"

ietfOneWayIpdv OBJECT-IDENTITY
    STATUS     current
    DESCRIPTION
        "Type-P-One-way-ipdv"
    REFERENCE " RFC3393, section 2."
    ::= { ianaIppmMetrics 27 }

ietfOneWayIpdvPoissonStream OBJECT-IDENTITY
    STATUS     current
    DESCRIPTION
        "Type-P-One-way-ipdv-Poisson-stream"
    REFERENCE " RFC3393, section 3."
    ::= { ianaIppmMetrics 28 }

ietfOneWayIpdvPercentile OBJECT-IDENTITY
    STATUS     current
    DESCRIPTION
      "Type-P-One-way-ipdv-percentile"
    REFERENCE " RFC3393, section 4.3."
    ::= { ianaIppmMetrics 29 }

ietfOneWayIpdvInversePercentile OBJECT-IDENTITY
    STATUS     current
    DESCRIPTION
        "Type-P-One-way-ipdv-inverse-percentile"
    REFERENCE " RFC3393, section 4.4."
    ::= { ianaIppmMetrics 30 }

ietfOneWayIpdvJitter OBJECT-IDENTITY
    STATUS     current
    DESCRIPTION
        "Type-P-One-way-ipdv-jitter"
    REFERENCE " RFC3393, section 4.5."
    ::= { ianaIppmMetrics 31 }

ietfOneWayPeakToPeakIpdv OBJECT-IDENTITY
    STATUS     current
    DESCRIPTION
        "Type-P-One-way-peak-to-peak-ipdv"
    REFERENCE " RFC3393, section 4.6."
    ::= { ianaIppmMetrics 32 }

--
-- RFC 3432: "Network performance measurement with periodic streams"
--

ietfOneWayDelayPeriodicStream OBJECT-IDENTITY
    STATUS     current
    DESCRIPTION
        "Type-P-One-way-Delay-Periodic-Stream"
    REFERENCE " RFC3432, section 4."
    ::= { ianaIppmMetrics 33 }

END
