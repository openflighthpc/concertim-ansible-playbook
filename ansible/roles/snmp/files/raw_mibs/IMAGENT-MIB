IMAGENT-MIB DEFINITIONS ::= BEGIN

IMPORTS
        enterprises, IpAddress, Gauge
                FROM RFC1155-SMI
        OBJECT-TYPE
                FROM RFC-1212
        TRAP-TYPE
                FROM RFC-1215
        DisplayString
                FROM RFC1213-MIB;

   jacarta  OBJECT IDENTIFIER ::= { enterprises 19011 }
   iM OBJECT IDENTIFIER ::= { jacarta 1 }

      iMSummary OBJECT IDENTIFIER  ::=  {  iM 1   }

         iMStatus OBJECT-TYPE
            SYNTAX  INTEGER {
               noStatus(1),
               normal(2),
               warning(3),
               critical(4),
               sensorError(5)
            }
            ACCESS  read-only
            STATUS  mandatory
            DESCRIPTION
            "The current status of this iM. The status of the iM is the worst status of all the sensors under the control of this iM."
            ::=  {  iMSummary 2   }

         iMManufName OBJECT-TYPE
            SYNTAX  DisplayString
            ACCESS  read-only
            STATUS  mandatory
            DESCRIPTION
            "The manufacturers name"
            ::=  {  iMSummary 6   }

         iMHelpUrl OBJECT-TYPE
            SYNTAX  DisplayString
            ACCESS  read-only
            STATUS  mandatory
            DESCRIPTION
            "The URL of the web based help"
            ::=  {  iMSummary 7   }

         iMProductName OBJECT-TYPE
            SYNTAX  DisplayString
            ACCESS  read-only
            STATUS  mandatory
            DESCRIPTION
            "The product name"
            ::=  {  iMSummary 8   }

         iMHostName OBJECT-TYPE
            SYNTAX  DisplayString
            ACCESS  read-write
            STATUS  mandatory
            DESCRIPTION
            "The hostname"
            ::=  {  iMSummary 9   }

      iMSensor OBJECT IDENTIFIER  ::=  {  iM 2 }

         iMDetail OBJECT IDENTIFIER ::= { iMSensor 2  }

            iMEntry OBJECT IDENTIFIER ::= { iMDetail 1  }

               iMHost OBJECT-TYPE
                  SYNTAX  IpAddress
                  ACCESS  read-write
                  STATUS  mandatory
                  DESCRIPTION
                  "The Host of this sensor, this is the IP address"
                  ::=  {  iMEntry 1   }

               iMUseDHCP OBJECT-TYPE
                  SYNTAX  INTEGER {
                     yes(1),
                     no(2)
                  }
                  ACCESS  read-write
                  STATUS  mandatory
                  DESCRIPTION
                  "To use DHCP enter a 1, to use a static IP address enter a 2"
                  ::=  {  iMEntry 2   }

               iMMAC OBJECT-TYPE
                  SYNTAX  DisplayString
                  ACCESS  read-only
                  STATUS  mandatory
                  DESCRIPTION
                  "The MAC address of this system"
                  ::=  {  iMEntry 3   }

               iMSetCommunity OBJECT-TYPE
                  SYNTAX  DisplayString
                  ACCESS  read-write
                  STATUS  mandatory
                  DESCRIPTION
                  "The iM community string used for snmp Sets"
                  ::=  {  iMEntry 4   }

               iMGetCommunity OBJECT-TYPE
                  SYNTAX  DisplayString
                  ACCESS  read-write
                  STATUS  mandatory
                  DESCRIPTION
                  "The iM community string used for snmp Gets"
                  ::=  {  iMEntry 5   }

               iMTempTable OBJECT-TYPE
                  SYNTAX  SEQUENCE OF IMTempEntry
                  ACCESS  not-accessible
                  STATUS  mandatory
                  DESCRIPTION
                  "This table contains the data for every Temperature Sensor in the SensorArray. Each row in the table contains data for a different Temperature Sensor."
                  ::=  {  iMEntry 16   }

               iMTempEntry OBJECT-TYPE
                  SYNTAX  IMTempEntry
                  ACCESS  not-accessible
                  STATUS  mandatory
                  DESCRIPTION
                  "This is an entry in the iMTempEntry Table"
                  INDEX         { iMTempIndex }
                  ::=  {  iMTempTable 1 }

                  IMTempEntry ::= SEQUENCE {
                     iMTempDescription
                        DisplayString,
                     iMTempLocation
                        DisplayString,
                     iMTempDegree
                        INTEGER,
                     iMTempStatus
                        INTEGER,
                     iMTempOnline
                        INTEGER,
                     iMTempGoOnline
                        INTEGER,
                     iMTempHighWarning
                        INTEGER,
                     iMTempHighCritical
                        INTEGER,
                     iMTempLowWarning
                        INTEGER,
                     iMTempLowCritical
                        INTEGER,
                     iMTempRearm
                        INTEGER,
                     iMTempDegreeType
                        INTEGER,
                     iMTempSensorType
                        INTEGER,
                     iMTempDegreeRaw
                        INTEGER,
                     iMTempEmailTrapLimit
                        INTEGER,
                     iMTempEmailTrapSchedule
                        DisplayString,
                     iMTempEmailTrapInterval
                        INTEGER,
                     iMTempSendNormalTrap
                        INTEGER,
                     iMTempDelayError
                        INTEGER,
                     iMTempDelayNormal
                        INTEGER,
                     iMTempIndex
                        INTEGER,
                     iMTempRelayCycleTime
                        INTEGER,
                     iMTempRelayOnPort
                        INTEGER,
                     iMTempRelayActiveStatus
                        INTEGER,
                     iMTempRelayAction
                        INTEGER,
                     iMTempEmailInterval
                        INTEGER,
                     iMTempIndexCount
                        INTEGER,
                     iMTempOffset
                        INTEGER,
                     iMTempSirenCycleTime
                        INTEGER,
                     iMTempSirenOnPort
                        INTEGER,
                     iMTempSirenActiveStatus
                        INTEGER,
                     iMTempSirenAction
                        INTEGER,
                     iMTempAcknowledgement
                        INTEGER,
                     iMTempSirenDelayAlarm
                        INTEGER,
                     iMTempURL
                        DisplayString,
                     iMTempOpenURL
                        INTEGER,
                     iMTempDatacollectType
                        INTEGER,
                     iMTempContTimeHighCritical
                        INTEGER,
                     iMTempContTimeHighWarning
                        INTEGER,
                     iMTempContTimeNormal
                        INTEGER,
                     iMTempContTimeLowWarning
                        INTEGER,
                     iMTempContTimeLowCritical
                        INTEGER,
                     iMTempContTimeSensorError
                        INTEGER,
                     iMTempCalendar
                        INTEGER,
                     iMThermostatIndex
                        INTEGER,
                     iMThermostatDescription
                        DisplayString,
                     iMThermostatValue
                        INTEGER,
                     iMThermostatOnline
                        INTEGER,
                     iMThermostatGoOnline
                        INTEGER,
                     iMThermostatMode
                        INTEGER,
                     iMThermostatRelayControlPort
                        INTEGER,
                     iMThermostatNormalAction1
                        INTEGER,
                     iMThermostatHighLimit1
                        INTEGER,
                     iMThermostatHighLimitAction1
                        INTEGER,
                     iMThermostatLowLimit1
                        INTEGER,
                     iMThermostatLowLimitAction1
                        INTEGER,
                     iMThermostatNormalAction2
                        INTEGER,
                     iMThermostatHighLimit2
                        INTEGER,
                     iMThermostatHighLimitAction2
                        INTEGER,
                     iMThermostatLowLimit2
                        INTEGER,
                     iMThermostatLowLimitAction2
                        INTEGER,
                     iMThermostatEnableTime
                        DisplayString,
                     iMTempSendNormalMail
                        INTEGER,
                     iMTempSendTrap
                        INTEGER,
                     iMTempSendMail
                        INTEGER
                  }
                  iMTempDescription OBJECT-TYPE
                     SYNTAX  DisplayString
                     ACCESS  read-write
                     STATUS  mandatory
                     DESCRIPTION
                     "A Description of this sensor"
                     ::=  {  iMTempEntry 1   }

                  iMTempLocation OBJECT-TYPE
                       SYNTAX  DisplayString
                       ACCESS  read-write
                       STATUS  mandatory
                       DESCRIPTION
                       "The physical location of this sensor"
                       ::=  {  iMTempEntry 2   }

                  iMTempDegree OBJECT-TYPE
                     SYNTAX  INTEGER
                     ACCESS  read-only
                     STATUS  mandatory
                     DESCRIPTION
                     "The degrees in this sensor"
                     ::=  {  iMTempEntry 3   }

                  iMTempStatus OBJECT-TYPE
                     SYNTAX  INTEGER {
                        noStatus(1),
                        normal(2),
                        highWarning(3),
                        highCritical(4),
                        lowWarning(5),
                        lowCritical(6),
                        sensorError(7)
                     }
                     ACCESS  read-only
                     STATUS  mandatory
                     DESCRIPTION
                     "The current status of this Sensor"
                     ::=  {  iMTempEntry 4   }
      
                  iMTempOnline OBJECT-TYPE
                     SYNTAX  INTEGER {
                        online(1),
                        offline(2)
                     }
                     ACCESS  read-only
                     STATUS  mandatory
                     DESCRIPTION
                     "If this Sensor is currently online"
                     ::=  {  iMTempEntry 5   }
   
                  iMTempGoOnline OBJECT-TYPE
                     SYNTAX  INTEGER {
                        goOnline(1),
                        goOffline(2)
                     }
                     ACCESS  read-write
                     STATUS  mandatory
                     DESCRIPTION
                     "To put online enter a 1, to take offline enter a 2"
                     ::=  {  iMTempEntry 6   }
         
                  iMTempHighWarning OBJECT-TYPE
                     SYNTAX  INTEGER
                     ACCESS  read-write
                     STATUS  mandatory
                     DESCRIPTION
                     "How hot this sensor gets before it sends a warning"
                     ::=  {  iMTempEntry 7   }
      
                  iMTempHighCritical OBJECT-TYPE
                     SYNTAX  INTEGER
                     ACCESS  read-write
                     STATUS  mandatory
                     DESCRIPTION
                     "How hot this sensor gets before it sends a critical event"
                     ::=  {  iMTempEntry 8   }
   
                  iMTempLowWarning OBJECT-TYPE
                     SYNTAX  INTEGER
                     ACCESS  read-write
                     STATUS  mandatory
                     DESCRIPTION
                     "How cold this sensor gets before it sends a warning"
                     ::=  {  iMTempEntry 9   }
   
                  iMTempLowCritical OBJECT-TYPE
                     SYNTAX  INTEGER
                     ACCESS  read-write
                     STATUS  mandatory
                     DESCRIPTION
                     "How cold this sensor gets before it sends a critical event"
                     ::=  {  iMTempEntry 10   }
      
                  iMTempRearm OBJECT-TYPE
                     SYNTAX  INTEGER
                     ACCESS  read-write
                     STATUS  mandatory
                     DESCRIPTION
                     "The number of degrees to rearm the status. For example if status goes from normal to warning, the temp must go down iMTempRearm degrees below warning before the status goes to normal"
                     ::=  {  iMTempEntry 11   }
   
                  iMTempDegreeType OBJECT-TYPE
                     SYNTAX  INTEGER {
                        fahr(0),
                        celsius(1)
                     }
                     ACCESS  read-write
                     STATUS  mandatory
                     DESCRIPTION
                     "The degrees are in fahrenheit(0) or in celsius(1)"
                     ::=  {  iMTempEntry 12   }
      
                  iMTempSensorType OBJECT-TYPE
                       SYNTAX  INTEGER {
                          type1(0),
                          type2(1)
                       }
                       ACCESS  read-write
                       STATUS  mandatory
                       DESCRIPTION
                       "The type of temperture sensor"
                       ::=  {  iMTempEntry 13   }
         
                  iMTempDegreeRaw OBJECT-TYPE
                     SYNTAX  INTEGER 
                     ACCESS  read-only
                     STATUS  mandatory
                     DESCRIPTION
                     "SP Only: The raw degree data from the temperature sensor, slightly higher resolution"
                     ::=  {  iMTempEntry 14   }

                  iMTempEmailTrapLimit OBJECT-TYPE
                     SYNTAX  INTEGER {
                        disable(0),
                        enable(1)
                     }
                     ACCESS  read-write
                     STATUS  mandatory
                     DESCRIPTION
                     "Enable email/trap limit feature"
                     ::=  {  iMTempEntry 16   }

                  iMTempEmailTrapSchedule OBJECT-TYPE
                     SYNTAX  DisplayString
                     ACCESS  read-write
                     STATUS  mandatory
                     DESCRIPTION
                     "SP Only: Email/trap limit schedule for this sensor"
                     ::=  {  iMTempEntry 17   }

                  iMTempEmailTrapInterval OBJECT-TYPE
                     SYNTAX  INTEGER (0..60)
                     ACCESS  read-write
                     STATUS  mandatory
                     DESCRIPTION
                     "Minimum time between each [email/trap:SP, only trap:CP8] (can be from 0 to 60 minutes)."
                     ::=  {  iMTempEntry 18   }

                  iMTempSendNormalTrap OBJECT-TYPE
                     SYNTAX  INTEGER {
                        disable(0),
                        enable(1)
                     }
                     ACCESS  read-write
                     STATUS  mandatory
                     DESCRIPTION
                     "Enable sending email/trap when sensor goes to normal"
                     ::=  {  iMTempEntry 19   }

                  iMTempDelayError OBJECT-TYPE
                     SYNTAX  INTEGER (0..65534)
                     ACCESS  read-write
                     STATUS  mandatory
                     DESCRIPTION
                     "Time in seconds after the sensor has been in error status before report as an error"
                     ::=  {  iMTempEntry 20   }

                  iMTempDelayNormal OBJECT-TYPE
                     SYNTAX  INTEGER (0..65534)
                     ACCESS  read-write
                     STATUS  mandatory
                     DESCRIPTION
                     "Time in seconds after the sensor change from error to normal before report as normal"
                     ::=  {  iMTempEntry 21   }

                  iMTempIndex OBJECT-TYPE
                     SYNTAX  INTEGER (0..7)
                     ACCESS  read-only
                     STATUS  mandatory
                     DESCRIPTION
                     "The index into the temperature sensor table"
                     ::=  {  iMTempEntry 22   }
                     
                  iMTempRelayCycleTime OBJECT-TYPE
                     SYNTAX INTEGER (1..255)
                     ACCESS read-write
                     STATUS mandatory
                     DESCRIPTION
                     "Relay toggle period in seconds for Cycle action."
                     ::= {  iMTempEntry 23 }

                  iMTempRelayOnPort OBJECT-TYPE
                     SYNTAX INTEGER (0..255)
                     ACCESS read-write
                     STATUS mandatory
                     DESCRIPTION
                     "The sensor port that the relay will listen to. If this is set to 255, then the relay will not listen to any sensor ports"
                     ::= {  iMTempEntry 24 }

                  iMTempRelayActiveStatus OBJECT-TYPE
                     SYNTAX INTEGER {
                        highWarning(3),
                        highCritical(4),
                        lowWarning(5),
                        lowCritical(6),
                        anyError(7)
                     }
                     ACCESS read-write
                     STATUS mandatory
                     DESCRIPTION
                     "Sensor status that will activate the relay"
                     ::= {  iMTempEntry 25 }

                  iMTempRelayAction OBJECT-TYPE
                     SYNTAX INTEGER {
                        cycle(2),
                        turn-on(3),
                        turn-off(4)
                     }
                     ACCESS read-write
                     STATUS mandatory
                     DESCRIPTION
                     "What the relay will do when the listened to port status turns to the specified active status."
                     ::= {  iMTempEntry 26 }

                  iMTempEmailInterval OBJECT-TYPE
                     SYNTAX  INTEGER (0..60)
                     ACCESS  read-write
                     STATUS  mandatory
                     DESCRIPTION
                     "CP8 Only: Minimum time between each email (can be from 0 to 60 minutes)"
                     ::=  {  iMTempEntry 27   }

                  iMTempIndexCount OBJECT-TYPE
                     SYNTAX  INTEGER
                     ACCESS  read-only
                     STATUS  mandatory
                     DESCRIPTION
                     "Number of Temperature sensor online"
                     ::=  {  iMTempEntry 28   }

                  iMTempOffset OBJECT-TYPE
                     SYNTAX  INTEGER
                     ACCESS  read-write
                     STATUS  mandatory
                     DESCRIPTION
                     "Temperature Offset reading"
                     ::=  {  iMTempEntry 29   }

                  iMTempSirenCycleTime OBJECT-TYPE
                     SYNTAX INTEGER (1..255)
                     ACCESS read-write
                     STATUS mandatory
                     DESCRIPTION
                     "Siren toggle period in seconds for Cycle action."
                     ::= {  iMTempEntry 30 }

                  iMTempSirenOnPort OBJECT-TYPE
                     SYNTAX INTEGER (0..255)
                     ACCESS read-write
                     STATUS mandatory
                     DESCRIPTION
                     "The sensor port that the siren will listen to. If this is set to 255, then the siren will not listen to any sensor ports"
                     ::= {  iMTempEntry 31 }

                  iMTempSirenActiveStatus OBJECT-TYPE
                     SYNTAX INTEGER {
                        highWarning(3),
                        highCritical(4),
                        lowWarning(5),
                        lowCritical(6),
                        anyError(7)
                     }
                     ACCESS read-write
                     STATUS mandatory
                     DESCRIPTION
                     "Sensor status that will activate the siren"
                     ::= {  iMTempEntry 32 }

                  iMTempSirenAction OBJECT-TYPE
                     SYNTAX INTEGER {
                        cycle(2),
                        turn-on(3),
                        turn-off(4)
                     }
                     ACCESS read-write
                     STATUS mandatory
                     DESCRIPTION
                     "What the siren will do when the listened to port status turns to the specified active status."
                     ::= {  iMTempEntry 33 }

                  iMTempAcknowledgement OBJECT-TYPE
                     SYNTAX INTEGER {
                        ack(1)
                     }
                     ACCESS read-write
                     STATUS mandatory
                     DESCRIPTION
                     "Acknowledged sensor error and stop notification"
                     ::= {  iMTempEntry 34 }

                  iMTempSirenDelayAlarm OBJECT-TYPE
                     SYNTAX INTEGER (1..255)
                     ACCESS read-write
                     STATUS mandatory
                     DESCRIPTION
                     "Siren delay in seconds before start Alarm."
                     ::= {  iMTempEntry 35 }

                  iMTempURL OBJECT-TYPE
                     SYNTAX  DisplayString
                     ACCESS  read-write
                     STATUS  mandatory
                     DESCRIPTION
                     "Sensor URL link."
                     ::= {  iMTempEntry 36 }

                  iMTempOpenURL OBJECT-TYPE
                     SYNTAX INTEGER {
                        cur-window(0),
                        new-window(2)
                     }
                     ACCESS read-write
                     STATUS mandatory
                     DESCRIPTION
                     "Open URL in this browser or open in a new window."
                     ::= {  iMTempEntry 37 }

                  iMTempDatacollectType OBJECT-TYPE
                     SYNTAX INTEGER {
                        average(1),
                        highest(2),
                        lowest(3)
                     }
                     ACCESS read-write
                     STATUS mandatory
                     DESCRIPTION
                     "Type of datacollect to collect."
                     ::= {  iMTempEntry 38 }

                  iMTempContTimeHighCritical OBJECT-TYPE
                     SYNTAX INTEGER (0..65535)
                     ACCESS read-write
                     STATUS mandatory
                     DESCRIPTION
                     "Continuous time for this sensor to be in High Critical before accepting new Status."
                     ::= {  iMTempEntry 39 }

                  iMTempContTimeHighWarning OBJECT-TYPE
                     SYNTAX INTEGER (0..65535)
                     ACCESS read-write
                     STATUS mandatory
                     DESCRIPTION
                     "Continuous time for this sensor to be in High Warning before accepting new Status."
                     ::= {  iMTempEntry 40 }

                  iMTempContTimeNormal OBJECT-TYPE
                     SYNTAX INTEGER (0..65535)
                     ACCESS read-write
                     STATUS mandatory
                     DESCRIPTION
                     "Continuous time for this sensor to be in Normal before accepting new Status."
                     ::= {  iMTempEntry 41 }

                  iMTempContTimeLowWarning OBJECT-TYPE
                     SYNTAX INTEGER (0..65535)
                     ACCESS read-write
                     STATUS mandatory
                     DESCRIPTION
                     "Continuous time for this sensor to be in Low Warning before accepting new Status."
                     ::= {  iMTempEntry 42 }

                  iMTempContTimeLowCritical OBJECT-TYPE
                     SYNTAX INTEGER (0..65535)
                     ACCESS read-write
                     STATUS mandatory
                     DESCRIPTION
                     "Continuous time for this sensor to be in Low Critical before accepting new Status."
                     ::= {  iMTempEntry 43 }

                  iMTempContTimeSensorError OBJECT-TYPE
                     SYNTAX INTEGER (0..65535)
                     ACCESS read-write
                     STATUS mandatory
                     DESCRIPTION
                     "Continuous time for this sensor to be in Sensor Error before accepting new Status."
                     ::= {  iMTempEntry 44 }

                  iMTempCalendar OBJECT-TYPE
                     SYNTAX INTEGER {
                        disable(0),
                        enable(1)
                     }
                     ACCESS read-write
                     STATUS mandatory
                     DESCRIPTION
                     "Enable or disable the calendar filtering working hours of sensor."
                     ::= {  iMTempEntry 45 }

                  iMThermostatIndex OBJECT-TYPE
                     SYNTAX  INTEGER
                     ACCESS  read-only
                     STATUS  mandatory
                     DESCRIPTION
                     "A unique value for each sensor thermostat port."
                     ::= {  iMTempEntry 46 }

                  iMThermostatDescription OBJECT-TYPE
                     SYNTAX  DisplayString
                     ACCESS  read-write
                     STATUS  mandatory
                     DESCRIPTION
                     "A Description of this sensor thermostat"
                     ::= {  iMTempEntry 47 }

                  iMThermostatValue OBJECT-TYPE
                     SYNTAX  INTEGER
                     ACCESS  read-only
                     STATUS  mandatory
                     DESCRIPTION
                     "The value in this sensor"
                     ::= {  iMTempEntry 48 }

                  iMThermostatOnline OBJECT-TYPE
                     SYNTAX  INTEGER {
                        online(1),
                        offline(2)
                     }
                     ACCESS  read-only
                     STATUS  mandatory
                     DESCRIPTION
                     "If this Sensor is currently online"
                     ::= {  iMTempEntry 49 }

                  iMThermostatGoOnline OBJECT-TYPE
                     SYNTAX  INTEGER {
                        goOnline(1),
                        goOffline(2)
                     }
                     ACCESS  read-write
                     STATUS  mandatory
                     DESCRIPTION
                     "To put online enter a 1, to take offline enter a 2"
                     ::= {  iMTempEntry 50 }

                  iMThermostatMode OBJECT-TYPE
                     SYNTAX INTEGER {
                        normal(0),
                        time-bases(1)
                     }
                     ACCESS read-write
                     STATUS mandatory
                     DESCRIPTION
                     "To select the thermostat mode for working on time-bases(1) or normal(0)."
                     ::= {  iMTempEntry 51 }

                  iMThermostatRelayControlPort OBJECT-TYPE
                     SYNTAX INTEGER
                     ACCESS read-write
                     STATUS mandatory
                     DESCRIPTION
                     "To select a relay port to be controled by this thermostat sensor."
                     ::= {  iMTempEntry 52 }

                  iMThermostatNormalAction1 OBJECT-TYPE
                     SYNTAX INTEGER {
                        turn-on(0),
                        turn-off(1),
                        no-change(2)
                     }
                     ACCESS read-write
                     STATUS mandatory
                     DESCRIPTION
                     "Profile1: Thermostat normal action for controlling a relay sensor."
                     ::= {  iMTempEntry 53 }

                  iMThermostatHighLimit1 OBJECT-TYPE
                     SYNTAX INTEGER (-40..167)
                     ACCESS read-write
                     STATUS mandatory
                     DESCRIPTION
                     "Profile1: When this sersor higher than thermostat high limit, it will take a high limit action."
                     ::= {  iMTempEntry 54 }

                  iMThermostatHighLimitAction1 OBJECT-TYPE
                     SYNTAX INTEGER {
                        turn-on(0),
                        turn-off(1),
                        no-change(2)
                     }
                     ACCESS read-write
                     STATUS mandatory
                     DESCRIPTION
                     "Profile1: Thermostat high limit action for controlling a relay sensor."
                     ::= {  iMTempEntry 55 }

                  iMThermostatLowLimit1 OBJECT-TYPE
                     SYNTAX INTEGER (-40..167)
                     ACCESS read-write
                     STATUS mandatory
                     DESCRIPTION
                     "Profile1: When this sersor higher than thermostat low limit, it will take a normal limit action."
                     ::= {  iMTempEntry 56 }

                  iMThermostatLowLimitAction1 OBJECT-TYPE
                     SYNTAX INTEGER {
                        turn-on(0),
                        turn-off(1),
                        no-change(2)
                     }
                     ACCESS read-write
                     STATUS mandatory
                     DESCRIPTION
                     "Profile1: Thermostat low limit action for controlling a relay sensor."
                     ::= {  iMTempEntry 57 }

                  iMThermostatNormalAction2 OBJECT-TYPE
                     SYNTAX INTEGER {
                        turn-on(0),
                        turn-off(1),
                        no-change(2)
                     }
                     ACCESS read-write
                     STATUS mandatory
                     DESCRIPTION
                     "Profile2: Thermostat normal action for controlling a relay sensor."
                     ::= {  iMTempEntry 58 }

                  iMThermostatHighLimit2 OBJECT-TYPE
                     SYNTAX INTEGER (-40..167)
                     ACCESS read-write
                     STATUS mandatory
                     DESCRIPTION
                     "Profile2: When this sersor higher than thermostat high limit, it will take a high limit action."
                     ::= {  iMTempEntry 59 }

                  iMThermostatHighLimitAction2 OBJECT-TYPE
                     SYNTAX INTEGER {
                        turn-on(0),
                        turn-off(1),
                        no-change(2)
                     }
                     ACCESS read-write
                     STATUS mandatory
                     DESCRIPTION
                     "Profile2: Thermostat high limit action for controlling a relay sensor."
                     ::= {  iMTempEntry 60 }

                  iMThermostatLowLimit2 OBJECT-TYPE
                     SYNTAX INTEGER (-40..167)
                     ACCESS read-write
                     STATUS mandatory
                     DESCRIPTION
                     "Profile2: When this sersor higher than thermostat low limit, it will take a normal limit action."
                     ::= {  iMTempEntry 61 }

                  iMThermostatLowLimitAction2 OBJECT-TYPE
                     SYNTAX INTEGER {
                        turn-on(0),
                        turn-off(1),
                        no-change(2)
                     }
                     ACCESS read-write
                     STATUS mandatory
                     DESCRIPTION
                     "Profile2: Thermostat low limit action for controlling a relay sensor."
                     ::= {  iMTempEntry 62 }

                  iMThermostatEnableTime OBJECT-TYPE
                     SYNTAX  DisplayString
                     ACCESS  read-write
                     STATUS  mandatory
                     DESCRIPTION
                     "Time to enable on Thermostat"
                     ::=  {  iMTempEntry 63 }

                  iMTempSendNormalMail OBJECT-TYPE
                     SYNTAX  INTEGER {
                        disable(0),
                        enable(1)
                     }
                     ACCESS  read-write
                     STATUS  mandatory
                     DESCRIPTION
                     "Enable sending email when sensor goes to normal"
                     ::=  {  iMTempEntry 64 }

                  iMTempSendTrap OBJECT-TYPE
                     SYNTAX  INTEGER {
                        disable(0),
                        enable(1)
                     }
                     ACCESS  read-write
                     STATUS  mandatory
                     DESCRIPTION
                     "Enable sending trap when sensor change status"
                     ::=  {  iMTempEntry 65 }

                  iMTempSendMail OBJECT-TYPE
                     SYNTAX  INTEGER {
                        disable(0),
                        enable(1)
                     }
                     ACCESS  read-write
                     STATUS  mandatory
                     DESCRIPTION
                     "Enable sending email when sensor change status"
                     ::=  {  iMTempEntry 66 }

               iMHumidityTable OBJECT-TYPE
                  SYNTAX  SEQUENCE OF IMHumidityEntry
                  ACCESS  not-accessible
                  STATUS  mandatory
                  DESCRIPTION
                  "This table contains the data for every Humidity Sensor in the SensorArray. Each row in the table contains data for a different Humidity Sensor."
                  ::=  {  iMEntry 17   }

               iMHumidityEntry OBJECT-TYPE
                  SYNTAX  IMHumidityEntry
                  ACCESS  not-accessible
                  STATUS  mandatory
                  DESCRIPTION
                  "This is an entry in the iMHumidityEntry Table"
                  INDEX         { iMHumidityIndex }
                  ::=  { iMHumidityTable 1 }

                  IMHumidityEntry ::= SEQUENCE {
                     iMHumidityDescription
                        DisplayString,
                       iMHumidityLocation
                          DisplayString,
                     iMHumidityPercent
                        INTEGER,
                     iMHumidityStatus
                        INTEGER,
                     iMHumidityOnline
                        INTEGER,
                     iMHumidityGoOnline
                        INTEGER,
                     iMHumidityHighWarning
                        INTEGER,
                     iMHumidityHighCritical
                        INTEGER,
                     iMHumidityLowWarning
                        INTEGER,
                     iMHumidityLowCritical
                        INTEGER,
                     iMHumidityRearm
                        INTEGER,
                     iMHumidityRaw
                        INTEGER,
                     iMHumidityLowVoltage
                        INTEGER,
                     iMHumidityHighVoltage
                        INTEGER,
                     iMHumidityEmailTrapLimit
                        INTEGER,
                     iMHumidityEmailTrapSchedule
                        DisplayString,
                     iMHumidityEmailTrapInterval
                        INTEGER,
                     iMHumiditySendNormalTrap
                        INTEGER,
                     iMHumidityDelayError
                        INTEGER,
                     iMHumidityDelayNormal
                        INTEGER,
                     iMHumidityIndex
                        INTEGER,
                     iMHumidityAtoDAmountMaxVoltage
                        INTEGER,
                     iMHumidityAtoDAmountBaseVoltage
                        INTEGER,
                     iMHumidityAtoDTypeUnit
                        INTEGER,
                     iMHumidityDcUnit
                        DisplayString,
                     iMHumidityAtoDJumper
                        INTEGER,
                     iMHumidityRelayCycleTime
                        INTEGER,
                     iMHumidityRelayOnPort
                        INTEGER,
                     iMHumidityRelayActiveStatus
                        INTEGER,
                     iMHumidityRelayAction
                        INTEGER,
                     iMHumidityEmailInterval
                        INTEGER,
                     iMHumidityIntelliVoltUnit
                        DisplayString,
                     iMHumidityIndexCount
                        INTEGER,
                     iMHumidityOffset
                        INTEGER,
                     iMHumiditySirenCycleTime
                        INTEGER,
                     iMHumiditySirenOnPort
                        INTEGER,
                     iMHumiditySirenActiveStatus
                        INTEGER,
                     iMHumiditySirenAction
                        INTEGER,
                     iMHumidityAcknowledgement
                        INTEGER,
                     iMHumiditySirenDelayAlarm
                        INTEGER,
                     iMHumidityURL
                        DisplayString,
                     iMHumidityOpenURL
                        INTEGER,
                     iMHumidityDatacollectType
                        INTEGER,
                     iMHumidityContTimeHighCritical
                        INTEGER,
                     iMHumidityContTimeHighWarning
                        INTEGER,
                     iMHumidityContTimeNormal
                        INTEGER,
                     iMHumidityContTimeLowWarning
                        INTEGER,
                     iMHumidityContTimeLowCritical
                        INTEGER,
                     iMHumidityContTimeSensorError
                        INTEGER,
                     iMHumidityCalendar
                        INTEGER,
                     iMHumiditySendNormalMail
                        INTEGER,
                     iMHumiditySendTrap
                        INTEGER,
                     iMHumiditySendMail
                        INTEGER
                  }
                  iMHumidityDescription OBJECT-TYPE
                     SYNTAX  DisplayString
                     ACCESS  read-write
                     STATUS  mandatory
                     DESCRIPTION
                     "A Description of this sensor"
                     ::=  {  iMHumidityEntry 1   }

                  iMHumidityLocation OBJECT-TYPE
                       SYNTAX  DisplayString
                       ACCESS  read-write
                       STATUS  mandatory
                       DESCRIPTION
                       "The physical location of this sensor"
                       ::=  {  iMHumidityEntry 2   }

                  iMHumidityPercent OBJECT-TYPE
                     SYNTAX  INTEGER (-32768..32767)
                     ACCESS  read-only
                     STATUS  mandatory
                     DESCRIPTION
                     "The relative humidity percentage measured by this sensor"
                     ::=  {  iMHumidityEntry 3   }

                  iMHumidityStatus OBJECT-TYPE
                     SYNTAX  INTEGER {
                        noStatus(1),
                        normal(2),
                        highWarning(3),
                        highCritical(4),
                        lowWarning(5),
                        lowCritical(6),
                        sensorError(7)
                     }
                     ACCESS  read-only
                     STATUS  mandatory
                     DESCRIPTION
                     "The current status of this Sensor"
                     ::=  {  iMHumidityEntry 4   }

                  iMHumidityOnline OBJECT-TYPE
                     SYNTAX  INTEGER {
                        online(1),
                        offline(2)
                     }
                     ACCESS  read-only
                     STATUS  mandatory
                     DESCRIPTION
                     "If this Sensor is currently online"
                        ::=  {  iMHumidityEntry 5   }

                  iMHumidityGoOnline OBJECT-TYPE
                     SYNTAX  INTEGER {
                        goOnline(1),
                        goOffline(2)
                     }
                     ACCESS  read-write
                     STATUS  mandatory
                     DESCRIPTION
                     "To put online enter a 1, to take offline enter a 2"
                     ::=  {  iMHumidityEntry 6   }

                  iMHumidityHighWarning OBJECT-TYPE
                     SYNTAX  INTEGER
                     ACCESS  read-write
                     STATUS  mandatory
                     DESCRIPTION
                     "How high the relative humidity this sensor measures before it sends a warning"
                     ::=  {  iMHumidityEntry 7   }

                  iMHumidityHighCritical OBJECT-TYPE
                     SYNTAX  INTEGER
                     ACCESS  read-write
                     STATUS  mandatory
                     DESCRIPTION
                     "How high the relative humidity this sensor measures before it becomes critical"
                     ::=  {  iMHumidityEntry 8   }

                  iMHumidityLowWarning OBJECT-TYPE
                     SYNTAX  INTEGER
                     ACCESS  read-write
                     STATUS  mandatory
                     DESCRIPTION
                     "How low the relative humidity this sensor measures before it sends a warning"
                     ::=  {  iMHumidityEntry 9   }

                  iMHumidityLowCritical OBJECT-TYPE
                     SYNTAX  INTEGER
                     ACCESS  read-write
                     STATUS  mandatory
                     DESCRIPTION
                     "How low the relative humidity this sensor measures before it becomes critical"
                     ::=  {  iMHumidityEntry 10   }

                  iMHumidityRearm OBJECT-TYPE
                     SYNTAX  INTEGER
                     ACCESS  read-write
                     STATUS  mandatory
                     DESCRIPTION
                     "The percent relative humidity to rearm the status. For example if status goes from normal to warning, the humidity must go down iMAnalogueRearm below warning before the status goes to normal"
                     ::=  {  iMHumidityEntry 11   }

                  iMHumidityRaw OBJECT-TYPE
                     SYNTAX  INTEGER 
                     ACCESS  read-only
                     STATUS  mandatory
                     DESCRIPTION
                     "The unformatted, raw, A/D value in this sensor. Contains more resolution than the formated percentage. This number can go from 0 to 1023 depending on the input voltage"
                     ::=  {  iMHumidityEntry 13   }

                  iMHumidityLowVoltage OBJECT-TYPE
                     SYNTAX  INTEGER
                     ACCESS  read-write
                     STATUS  mandatory
                     DESCRIPTION
                     "SP Only: The low voltage range for use in AtoD conversion."
                     ::=  {  iMHumidityEntry 14   }

                  iMHumidityHighVoltage OBJECT-TYPE
                     SYNTAX  INTEGER
                     ACCESS  read-write
                     STATUS  mandatory
                     DESCRIPTION
                     "SP Only: The high voltage range for use in AtoD conversion."
                     ::=  {  iMHumidityEntry 15   }

                  iMHumidityEmailTrapLimit OBJECT-TYPE
                     SYNTAX  INTEGER {
                        disable(0),
                        enable(1)
                     }
                     ACCESS  read-write
                     STATUS  mandatory
                     DESCRIPTION
                     "Enable email/trap limit feature"
                     ::=  {  iMHumidityEntry 17   }

                  iMHumidityEmailTrapSchedule OBJECT-TYPE
                     SYNTAX  DisplayString
                     ACCESS  read-write
                     STATUS  mandatory
                     DESCRIPTION
                     "SP Only: Email/trap limit schedule for this sensor"
                     ::=  {  iMHumidityEntry 18   }

                  iMHumidityEmailTrapInterval OBJECT-TYPE
                     SYNTAX  INTEGER (0..60)
                     ACCESS  read-write
                     STATUS  mandatory
                     DESCRIPTION
                     "Minimum time between each [email/trap:SP, only trap:CP8] (can be from 0 to 60 minutes)"
                     ::=  {  iMHumidityEntry 19   }

                  iMHumiditySendNormalTrap OBJECT-TYPE
                     SYNTAX  INTEGER {
                        disable(0),
                        enable(1)
                     }
                     ACCESS  read-write
                     STATUS  mandatory
                     DESCRIPTION
                     "Enable sending email/trap when sensor goes to normal"
                     ::=  {  iMHumidityEntry 20   }

                  iMHumidityDelayError OBJECT-TYPE
                     SYNTAX  INTEGER (0..65534)
                     ACCESS  read-write
                     STATUS  mandatory
                     DESCRIPTION
                     "Time in seconds after the sensor has been in error status before report as an error"
                     ::=  {  iMHumidityEntry 21   }

                  iMHumidityDelayNormal OBJECT-TYPE
                     SYNTAX  INTEGER (0..65534)
                     ACCESS  read-write
                     STATUS  mandatory
                     DESCRIPTION
                     "Time in seconds after the sensor change from error to normal before report as normal"
                     ::=  {  iMHumidityEntry 22   }

                  iMHumidityIndex OBJECT-TYPE
                     SYNTAX  INTEGER (0..7)
                     ACCESS  read-only
                     STATUS  mandatory
                     DESCRIPTION
                     "The index into the Humidity sensor table"
                     ::=  {  iMHumidityEntry 23   }

                  iMHumidityAtoDAmountMaxVoltage OBJECT-TYPE
                     SYNTAX  INTEGER
                     ACCESS  read-write
                     STATUS  mandatory
                     DESCRIPTION
                     "The maximum scale of IntelliAmp conversion."
                     ::=  {  iMHumidityEntry 24   }

                  iMHumidityAtoDAmountBaseVoltage OBJECT-TYPE
                     SYNTAX  INTEGER
                     ACCESS  read-write
                     STATUS  mandatory
                     DESCRIPTION
                     "The base scale of IntelliAmp conversion."
                     ::=  {  iMHumidityEntry 25   }

                  iMHumidityAtoDTypeUnit OBJECT-TYPE
                     SYNTAX  INTEGER {
                        absolute(1),
                        percent(2)
                     }
                     ACCESS  read-write
                     STATUS  mandatory
                     DESCRIPTION
                     "Type of scale for use in IntelliAmp conversion."
                     ::=  {  iMHumidityEntry 26   }
                
                  iMHumidityDcUnit OBJECT-TYPE
                     SYNTAX  DisplayString
                     ACCESS  read-write
                     STATUS  mandatory
                     DESCRIPTION
                     "Display unit in IntelliAmp conversion."
                     ::=  {  iMHumidityEntry 27   }

                  iMHumidityAtoDJumper OBJECT-TYPE
                     SYNTAX  INTEGER {
                        jumperAt-60(-600),
                        jumperAt-40(-400),
                        jumperAt-30(-300),
                        jumperAt-20(-200),
                        jumperAt-10(-100),
                        jumperAt10(100),
                        jumperAt20(200),
                        jumperAt30(300),
                        jumperAt40(400),
                        jumperAt60(600)
                     }
                     ACCESS  read-write
                     STATUS  mandatory
                     DESCRIPTION
                     "Selected voltage scale (jumper 0) in IntelliAmp conversion."
                     ::=  {  iMHumidityEntry 28   }

                  iMHumidityRelayCycleTime OBJECT-TYPE
                     SYNTAX INTEGER (1..255)
                     ACCESS read-write
                     STATUS mandatory
                     DESCRIPTION
                     "Relay toggle period in seconds for Cycle action."
                     ::=  {  iMHumidityEntry 29   }

                  iMHumidityRelayOnPort OBJECT-TYPE
                     SYNTAX INTEGER (0..255)
                     ACCESS read-write
                     STATUS mandatory
                     DESCRIPTION
                     "The sensor port that the relay will listen to. If this is set to 255, then the relay will not listen to any sensor ports"
                     ::=  {  iMHumidityEntry 30   }

                  iMHumidityRelayActiveStatus OBJECT-TYPE
                     SYNTAX INTEGER {
                        highWarning(3),
                        highCritical(4),
                        lowWarning(5),
                        lowCritical(6),
                        anyError(7)
                     }
                     ACCESS read-write
                     STATUS mandatory
                     DESCRIPTION
                     "Sensor status that will activate the relay"
                     ::=  {  iMHumidityEntry 31   }

                  iMHumidityRelayAction OBJECT-TYPE
                     SYNTAX INTEGER {
                        cycle(2),
                        turn-on(3),
                        turn-off(4)
                     }
                     ACCESS read-write
                     STATUS mandatory
                     DESCRIPTION
                     "What the relay will do when the listened to port status turns to the specified active status."
                     ::=  {  iMHumidityEntry 32   }

                  iMHumidityEmailInterval OBJECT-TYPE
                     SYNTAX  INTEGER (0..60)
                     ACCESS  read-write
                     STATUS  mandatory
                     DESCRIPTION
                     "CP8 Only: Minimum time between each emial (can be from 0 to 60 minutes)"
                     ::=  {  iMHumidityEntry 33   }

                  iMHumidityIntelliVoltUnit OBJECT-TYPE
                     SYNTAX  DisplayString
                     ACCESS  read-write
                     STATUS  mandatory
                     DESCRIPTION
                     "Display unit in IntelliVolt conversion."
                     ::=  {  iMHumidityEntry 34   }

                  iMHumidityIndexCount OBJECT-TYPE
                     SYNTAX  INTEGER
                     ACCESS   read-only
                     STATUS  mandatory
                     DESCRIPTION
                     "Number of Humidity sensor online"
                     ::=  {  iMHumidityEntry 35   }

                  iMHumidityOffset OBJECT-TYPE
                     SYNTAX  INTEGER
                     ACCESS  read-write
                     STATUS  mandatory
                     DESCRIPTION
                     "Humidity Offset reading"
                     ::=  {  iMHumidityEntry 36   }

                  iMHumiditySirenCycleTime OBJECT-TYPE
                     SYNTAX INTEGER (1..255)
                     ACCESS read-write
                     STATUS mandatory
                     DESCRIPTION
                     "Siren toggle period in seconds for Cycle action."
                     ::=  {  iMHumidityEntry 37   }

                  iMHumiditySirenOnPort OBJECT-TYPE
                     SYNTAX INTEGER (0..255)
                     ACCESS read-write
                     STATUS mandatory
                     DESCRIPTION
                     "The sensor port that the siren will listen to. If this is set to 255, then the siren will not listen to any sensor ports"
                     ::=  {  iMHumidityEntry 38   }

                  iMHumiditySirenActiveStatus OBJECT-TYPE
                     SYNTAX INTEGER {
                        highWarning(3),
                        highCritical(4),
                        lowWarning(5),
                        lowCritical(6),
                        anyError(7)
                     }
                     ACCESS read-write
                     STATUS mandatory
                     DESCRIPTION
                     "Sensor status that will activate the siren"
                     ::=  {  iMHumidityEntry 39   }

                  iMHumiditySirenAction OBJECT-TYPE
                     SYNTAX INTEGER {
                        cycle(2),
                        turn-on(3),
                        turn-off(4)
                     }
                     ACCESS read-write
                     STATUS mandatory
                     DESCRIPTION
                     "What the siren will do when the listened to port status turns to the specified active status."
                     ::=  {  iMHumidityEntry 40   }

                  iMHumidityAcknowledgement OBJECT-TYPE
                     SYNTAX INTEGER {
                        ack(1)
                     }
                     ACCESS read-write
                     STATUS mandatory
                     DESCRIPTION
                     "Acknowledged sensor error and stop notification"
                     ::= {  iMHumidityEntry 41 }

                  iMHumiditySirenDelayAlarm OBJECT-TYPE
                     SYNTAX INTEGER (1..255)
                     ACCESS read-write
                     STATUS mandatory
                     DESCRIPTION
                     "Siren delay in seconds before start Alarm."
                     ::=  {  iMHumidityEntry 42 }

                  iMHumidityURL OBJECT-TYPE
                     SYNTAX  DisplayString
                     ACCESS  read-write
                     STATUS  mandatory
                     DESCRIPTION
                     "Sensor URL link."
                     ::=  {  iMHumidityEntry 43 }

                  iMHumidityOpenURL OBJECT-TYPE
                     SYNTAX INTEGER {
                        cur-window(0),
                        new-window(2)
                     }
                     ACCESS  read-write
                     STATUS  mandatory
                     DESCRIPTION
                     "Open URL in this browser or open in a new window."
                     ::=  {  iMHumidityEntry 44 }

                  iMHumidityDatacollectType OBJECT-TYPE
                     SYNTAX INTEGER {
                        average(1),
                        highest(2),
                        lowest(3)
                     }
                     ACCESS  read-write
                     STATUS  mandatory
                     DESCRIPTION
                     "Type of datacollect to collect."
                     ::=  {  iMHumidityEntry 45 }

                  iMHumidityContTimeHighCritical OBJECT-TYPE
                     SYNTAX INTEGER (0..65535)
                     ACCESS read-write
                     STATUS mandatory
                     DESCRIPTION
                     "Continuous time for this sensor to be in High Critical before accepting new Status."
                     ::= {  iMHumidityEntry 46 }

                  iMHumidityContTimeHighWarning OBJECT-TYPE
                     SYNTAX INTEGER (0..65535)
                     ACCESS read-write
                     STATUS mandatory
                     DESCRIPTION
                     "Continuous time for this sensor to be in High Warning before accepting new Status."
                     ::= {  iMHumidityEntry 47 }

                  iMHumidityContTimeNormal OBJECT-TYPE
                     SYNTAX INTEGER (0..65535)
                     ACCESS read-write
                     STATUS mandatory
                     DESCRIPTION
                     "Continuous time for this sensor to be in Normal before accepting new Status."
                     ::= {  iMHumidityEntry 48 }

                  iMHumidityContTimeLowWarning OBJECT-TYPE
                     SYNTAX INTEGER (0..65535)
                     ACCESS read-write
                     STATUS mandatory
                     DESCRIPTION
                     "Continuous time for this sensor to be in Low Warning before accepting new Status."
                     ::= {  iMHumidityEntry 49 }

                  iMHumidityContTimeLowCritical OBJECT-TYPE
                     SYNTAX INTEGER (0..65535)
                     ACCESS read-write
                     STATUS mandatory
                     DESCRIPTION
                     "Continuous time for this sensor to be in Low Critical before accepting new Status."
                     ::= {  iMHumidityEntry 50 }

                  iMHumidityContTimeSensorError OBJECT-TYPE
                     SYNTAX INTEGER (0..65535)
                     ACCESS read-write
                     STATUS mandatory
                     DESCRIPTION
                     "Continuous time for this sensor to be in Sensor Error before accepting new Status."
                     ::= {  iMHumidityEntry 51 }

                  iMHumidityCalendar OBJECT-TYPE
                     SYNTAX INTEGER {
                        disable(0),
                        enable(1)
                     }
                     ACCESS read-write
                     STATUS mandatory
                     DESCRIPTION
                     "Enable or disable the calendar filtering working hours of sensor."
                     ::= {  iMHumidityEntry 52 }

                  iMHumiditySendNormalMail OBJECT-TYPE
                     SYNTAX  INTEGER {
                        disable(0),
                        enable(1)
                     }
                     ACCESS  read-write
                     STATUS  mandatory
                     DESCRIPTION
                     "Enable sending email when sensor goes to normal"
                     ::=  {  iMHumidityEntry 53 }

                  iMHumiditySendTrap OBJECT-TYPE
                     SYNTAX  INTEGER {
                        disable(0),
                        enable(1)
                     }
                     ACCESS  read-write
                     STATUS  mandatory
                     DESCRIPTION
                     "Enable sending trap when sensor change status"
                     ::=  {  iMHumidityEntry 54 }

                  iMHumiditySendMail OBJECT-TYPE
                     SYNTAX  INTEGER {
                        disable(0),
                        enable(1)
                     }
                     ACCESS  read-write
                     STATUS  mandatory
                     DESCRIPTION
                     "Enable sending email when sensor change status"
                     ::=  {  iMHumidityEntry 55 }

               iMSwitchTable OBJECT-TYPE
                  SYNTAX  SEQUENCE OF IMSwitchEntry
                  ACCESS  not-accessible
                  STATUS  mandatory
                  DESCRIPTION
                  "This table contains the data for every Switch Sensor in the SensorArray. Each row in the table contains data for a different Switch Sensor."
                  ::=  {  iMEntry 18   }

               iMSwitchEntry OBJECT-TYPE
                  SYNTAX  IMSwitchEntry
                  ACCESS  not-accessible
                  STATUS  mandatory
                  DESCRIPTION
                  "This is an entry in the iMSwitchEntry Table"
                  INDEX         { iMSwitchIndex }
                  ::=  { iMSwitchTable 1 }

                  IMSwitchEntry ::= SEQUENCE {
                     iMSwitchDescription
                        DisplayString,
                     iMSwitchLocation
                        DisplayString,
                     iMSwitchStatus
                        INTEGER,
                     iMSwitchOnline
                        INTEGER,
                     iMSwitchGoOnline
                        INTEGER,
                     iMSwitchDirection
                        INTEGER,
                     iMSwitchNormalState
                        INTEGER,
                     iMSwitchOutputLevel
                        INTEGER,
                     iMSensorType
                        INTEGER,
                     iMSwitchEmailTrapLimit
                        INTEGER,
                     iMSwitchEmailTrapSchedule
                        DisplayString,
                     iMSwitchEmailTrapInterval
                        INTEGER,
                     iMSwitchSendNormalTrap
                        INTEGER,
                     iMSwitchDelayError
                        INTEGER,
                     iMSwitchDelayNormal
                        INTEGER,
                     iMSwitchIndex
                        INTEGER,
                     iMSwitchRelayCycleTime
                        INTEGER,
                     iMSwitchRelayOnPort
                        INTEGER,
                     iMSwitchRelayActiveStatus
                        INTEGER,
                     iMSwitchRelayAction
                        INTEGER,
                     iMSwitchEmailInterval
                        INTEGER,
                     iMSwitchRelayOutputVoltStatus
                        INTEGER,
                     iMSwitchManualRelayCycleTime
                        INTEGER,
                     iMSwitchManualRelayAction
                        INTEGER,
                     iMSwitchRelayDescOn
                        DisplayString,
                     iMSwitchRelayDescOff
                        DisplayString,
                     iMSwitchIndexCount
                        INTEGER,
                     iMSwitchSirenCycleTime
                        INTEGER,
                     iMSwitchSirenOnPort
                        INTEGER,
                     iMSwitchSirenActiveStatus
                        INTEGER,
                     iMSwitchSirenAction
                        INTEGER,
                     iMSwitchAcknowledgement
                        INTEGER,
                     iMSwitchSirenDelayAlarm
                        INTEGER,
                     iMSwitchURL
                        DisplayString,
                     iMSwitchOpenURL
                        INTEGER,
                     iMSwitchContTimeHighCritical
                        INTEGER,
                     iMSwitchContTimeNormal
                        INTEGER,
                     iMSwitchCalendar
                        INTEGER,
                     iMSwitchRelayControlMode
                        INTEGER,
                     iMSwitchSirenControlMode
                        INTEGER,
                     iMSwitchSendNormalMail
                        INTEGER,
                     iMSwitchSendTrap
                        INTEGER,
                     iMSwitchSendMail
                        INTEGER
                  }
                  iMSwitchDescription OBJECT-TYPE
                     SYNTAX  DisplayString
                     ACCESS  read-write
                     STATUS  mandatory
                     DESCRIPTION
                     "A Description of this sensor Switch"
                     ::=  {  iMSwitchEntry 1   }

                    iMSwitchLocation OBJECT-TYPE
                       SYNTAX  DisplayString
                       ACCESS  read-write
                       STATUS  mandatory
                       DESCRIPTION
                       "The physical location of this sensor Switch"
                       ::=  {  iMSwitchEntry 2   }

                  iMSwitchStatus OBJECT-TYPE
                     SYNTAX  INTEGER {
                        noStatus(1),
                        normal(2),
                        highCritical(4),
                        lowCritical(6),
                        sensorError(7),
                        relayOn(8),
                        relayOff(9)
                     }
                     ACCESS  read-only
                     STATUS  mandatory
                     DESCRIPTION
                     "The current status of this Sensor, only input switches have a status"
                     ::=  {  iMSwitchEntry 3  }

                  iMSwitchOnline OBJECT-TYPE
                     SYNTAX  INTEGER {
                        online(1),
                        offline(2)
                     }
                     ACCESS  read-only
                     STATUS  mandatory
                     DESCRIPTION
                     "If this Sensor is currently online"
                        ::=  {  iMSwitchEntry 4  }

                  iMSwitchGoOnline OBJECT-TYPE
                     SYNTAX  INTEGER {
                        goOnline(1),
                        goOffline(2)
                     }
                     ACCESS  read-write
                     STATUS  mandatory
                     DESCRIPTION
                     "To put online enter a 1, to take offline enter a 2"
                     ::=  {  iMSwitchEntry 5  }

                  iMSwitchDirection OBJECT-TYPE
                     SYNTAX  INTEGER {
                        input(0),
                        output(1)
                     }
                     ACCESS  read-write
                     STATUS  mandatory
                     DESCRIPTION
                     "To set a switch to input enter 0. To set a switch to output enter 1"
                     ::=  {  iMSwitchEntry 6  }

                  iMSwitchNormalState OBJECT-TYPE
                     SYNTAX  INTEGER {
                        closed(0),
                        open(1)
                     }
                     ACCESS  read-write
                     STATUS  mandatory
                     DESCRIPTION
                     "The normal state of an input switch. If an input switch is in this state it is normal, else it is critical. An open switch senses +5 volts. A closed switch senses 0 volts."
                     ::=  {  iMSwitchEntry 7  }
                     
                  iMSwitchOutputLevel OBJECT-TYPE
                     SYNTAX  INTEGER {
                        low(0),
                        high(1)
                     }
                     ACCESS  read-write
                     STATUS  mandatory
                     DESCRIPTION
                     "An output swith can be set to this level"
                     ::=  {  iMSwitchEntry 8  }
                     
                  iMSensorType OBJECT-TYPE
                     SYNTAX  INTEGER {
                        temperature(1),
                        intellivolt(2),
                        humidity(3),
                        water(4),
                        intelliamp(5),
                        security(6),
                        airflow(8),
                        siren(9),
                        drycontact(10),
                        acvoltage(12),
                        relay(13),
                        motion(14),
                        smoke(24),
                        virtual(30)
                     }

                     ACCESS  read-write
                     STATUS  mandatory
                     DESCRIPTION
                     "Enter the type of this Sensor"
                     ::=  {  iMSwitchEntry 9  }

                  iMSwitchEmailTrapLimit OBJECT-TYPE
                     SYNTAX  INTEGER {
                        disable(0),
                        enable(1)
                     }
                     ACCESS  read-write
                     STATUS  mandatory
                     DESCRIPTION
                     "Enable email/trap limit feature"
                     ::=  {  iMSwitchEntry 11   }

                  iMSwitchEmailTrapSchedule OBJECT-TYPE
                     SYNTAX  DisplayString
                     ACCESS  read-write
                     STATUS  mandatory
                     DESCRIPTION
                     "SP Only: Email/trap limit schedule for this sensor"
                     ::=  {  iMSwitchEntry 12   }

                  iMSwitchEmailTrapInterval OBJECT-TYPE
                     SYNTAX  INTEGER (0..60)
                     ACCESS  read-write
                     STATUS  mandatory
                     DESCRIPTION
                     "Minimum time between each [email/trap:SP, only trap:CP8] (can be from 0 to 60 minutes)"
                     ::=  {  iMSwitchEntry 13   }

                  iMSwitchSendNormalTrap OBJECT-TYPE
                     SYNTAX  INTEGER {
                        disable(0),
                        enable(1)
                     }
                     ACCESS  read-write
                     STATUS  mandatory
                     DESCRIPTION
                     "Enable sending email/trap when sensor goes to normal"
                     ::=  {  iMSwitchEntry 14   }

                  iMSwitchDelayError OBJECT-TYPE
                     SYNTAX  INTEGER (0..65534)
                     ACCESS  read-write
                     STATUS  mandatory
                     DESCRIPTION
                     "Time in seconds after the sensor has been in error status before report as an error"
                     ::=  {  iMSwitchEntry 15   }

                  iMSwitchDelayNormal OBJECT-TYPE
                     SYNTAX  INTEGER (0..65534)
                     ACCESS  read-write
                     STATUS  mandatory
                     DESCRIPTION
                     "Time in seconds after the sensor change from error to normal before report as normal"
                     ::=  {  iMSwitchEntry 16   }

                  iMSwitchIndex OBJECT-TYPE
                     SYNTAX  INTEGER (0..67)
                     ACCESS  read-only
                     STATUS  mandatory
                     DESCRIPTION
                     "The index into the Switch sensor table"
                     ::=  {  iMSwitchEntry 17   }

                  iMSwitchRelayCycleTime OBJECT-TYPE
                     SYNTAX INTEGER (1..255)
                     ACCESS read-write
                     STATUS mandatory
                     DESCRIPTION
                     "Relay toggle period in seconds for Cycle action."
                     ::=  {  iMSwitchEntry 18   }

                  iMSwitchRelayOnPort OBJECT-TYPE
                     SYNTAX INTEGER (0..255)
                     ACCESS read-write
                     STATUS mandatory
                     DESCRIPTION
                     "The sensor port that the relay will listen to. If this is set to 255, then the relay will not listen to any sensor ports"
                     ::=  {  iMSwitchEntry 19   }

                  iMSwitchRelayActiveStatus OBJECT-TYPE
                     SYNTAX INTEGER {
                        highWarning(3),
                        highCritical(4),
                        lowWarning(5),
                        lowCritical(6),
                        anyError(7)
                     }
                     ACCESS read-write
                     STATUS mandatory
                     DESCRIPTION
                     "Sensor status that will activate the relay"
                     ::=  {  iMSwitchEntry 20   }

                  iMSwitchRelayAction OBJECT-TYPE
                     SYNTAX INTEGER {
                        cycle(2),
                        turn-on(3),
                        turn-off(4)
                     }
                     ACCESS read-write
                     STATUS mandatory
                     DESCRIPTION
                     "What the relay will do when the listened to port status turns to the specified active status."
                     ::=  {  iMSwitchEntry 21   }

                  iMSwitchEmailInterval OBJECT-TYPE
                     SYNTAX  INTEGER (0..60)
                     ACCESS  read-write
                     STATUS  mandatory
                     DESCRIPTION
                     "CP8 Only: Minimum time between each email (can be from 0 to 60 minutes)"
                     ::=  {  iMSwitchEntry 22   }

                  iMSwitchRelayOutputVoltStatus OBJECT-TYPE
                     SYNTAX  INTEGER {
                        sensorError(7),
                        noVoltagePresent(10),
                        voltagePresent(11)
                     }
                     ACCESS  read-only
                     STATUS  mandatory
                     DESCRIPTION
                     "SP Only: The current voltage status of the relay"
                        ::=  {  iMSwitchEntry 23  }

                  iMSwitchManualRelayCycleTime OBJECT-TYPE
                     SYNTAX INTEGER (1..255)
                     ACCESS read-write
                     STATUS mandatory
                     DESCRIPTION
                     "Relay toggle period in seconds for Manual Cycle action."
                     ::= { iMSwitchEntry 24 }

                  iMSwitchManualRelayAction OBJECT-TYPE
                     SYNTAX INTEGER {
                        allow-sensor-control(1),
                        turn-on(3),
                        turn-off(4),
                        cycle-Off-On-Off(7),
                        cycle-On-Off-On(8)
                     }
                     ACCESS read-write
                     STATUS mandatory
                     DESCRIPTION
                     "Control the relay manualy"
                     ::= { iMSwitchEntry 25 }

                  iMSwitchRelayDescOn OBJECT-TYPE
                     SYNTAX  DisplayString
                     ACCESS  read-write
                     STATUS  mandatory
                     DESCRIPTION
                     "Description of relay On"
                     ::=  {  iMSwitchEntry 26   }

                  iMSwitchRelayDescOff OBJECT-TYPE
                     SYNTAX  DisplayString
                     ACCESS  read-write
                     STATUS  mandatory
                     DESCRIPTION
                     "Description of relay Off"
                     ::=  {  iMSwitchEntry 27   }

                  iMSwitchIndexCount OBJECT-TYPE
                     SYNTAX  INTEGER
                     ACCESS  read-only
                     STATUS  mandatory
                     DESCRIPTION
                     "Number of Switch sensor online"
                     ::=  {  iMSwitchEntry 28   }

                  iMSwitchSirenCycleTime OBJECT-TYPE
                     SYNTAX INTEGER (1..255)
                     ACCESS read-write
                     STATUS mandatory
                     DESCRIPTION
                     "Siren toggle period in seconds for Cycle action."
                     ::=  {  iMSwitchEntry 29   }

                  iMSwitchSirenOnPort OBJECT-TYPE
                     SYNTAX INTEGER (0..255)
                     ACCESS read-write
                     STATUS mandatory
                     DESCRIPTION
                     "The sensor port that the siren will listen to. If this is set to 255, then the siren will not listen to any sensor ports"
                     ::=  {  iMSwitchEntry 30   }

                  iMSwitchSirenActiveStatus OBJECT-TYPE
                     SYNTAX INTEGER {
                        highWarning(3),
                        highCritical(4),
                        lowWarning(5),
                        lowCritical(6),
                        anyError(7)
                     }
                     ACCESS read-write
                     STATUS mandatory
                     DESCRIPTION
                     "Sensor status that will activate the siren"
                     ::=  {  iMSwitchEntry 31   }

                  iMSwitchSirenAction OBJECT-TYPE
                     SYNTAX INTEGER {
                        cycle(2),
                        turn-on(3),
                        turn-off(4)
                     }
                     ACCESS read-write
                     STATUS mandatory
                     DESCRIPTION
                     "What the siren will do when the listened to port status turns to the specified active status."
                     ::=  {  iMSwitchEntry 32   }

                  iMSwitchAcknowledgement OBJECT-TYPE
                     SYNTAX INTEGER {
                        ack(1)
                     }
                     ACCESS read-write
                     STATUS mandatory
                     DESCRIPTION
                     "Acknowledged sensor error and stop notification"
                     ::= {  iMSwitchEntry 33 }

                  iMSwitchSirenDelayAlarm OBJECT-TYPE
                     SYNTAX INTEGER (1..255)
                     ACCESS read-write
                     STATUS mandatory
                     DESCRIPTION
                     "Siren delay in seconds before start Alarm."
                     ::=  {  iMSwitchEntry 34   }

                  iMSwitchURL OBJECT-TYPE
                     SYNTAX  DisplayString
                     ACCESS  read-write
                     STATUS  mandatory
                     DESCRIPTION
                     "Sensor URL link."
                     ::=  {  iMSwitchEntry 35 }

                  iMSwitchOpenURL OBJECT-TYPE
                     SYNTAX  INTEGER {
                        cur-window(0),
                        new-window(2)
                     }
                     ACCESS  read-write
                     STATUS  mandatory
                     DESCRIPTION
                     "Open URL in this browser or open in a new window."
                     ::=  {  iMSwitchEntry 36 }

                  iMSwitchContTimeHighCritical OBJECT-TYPE
                     SYNTAX INTEGER (0..65535)
                     ACCESS read-write
                     STATUS mandatory
                     DESCRIPTION
                     "Continuous time for this sensor to be in High Critical before accepting new Status."
                     ::= {  iMSwitchEntry 37 }

                  iMSwitchContTimeNormal OBJECT-TYPE
                     SYNTAX INTEGER (0..65535)
                     ACCESS read-write
                     STATUS mandatory
                     DESCRIPTION
                     "Continuous time for this sensor to be in Normal before accepting new Status."
                     ::= {  iMSwitchEntry 39 }

                  iMSwitchCalendar OBJECT-TYPE
                     SYNTAX INTEGER {
                        disable(0),
                        enable(1)
                     }
                     ACCESS read-write
                     STATUS mandatory
                     DESCRIPTION
                     "Enable or disable the calendar filtering working hours of sensor."
                     ::= {  iMSwitchEntry 43 }

                  iMSwitchRelayControlMode OBJECT-TYPE
                     SYNTAX  INTEGER {
                        manual-control(0),
                        notification-control(1),
                        time-control(2),
                        thermostat-control(3)
                     }
                     ACCESS  read-write
                     STATUS  mandatory
                     DESCRIPTION
                     "Relay Control Mode used for selecting the mode to control a relay."
                     ::=  {  iMSwitchEntry 44  }

                  iMSwitchSirenControlMode OBJECT-TYPE
                     SYNTAX  INTEGER {
                        manual-control(0),
                        notification-control(1),
                        time-control(2)
                     }
                     ACCESS  read-write
                     STATUS  mandatory
                     DESCRIPTION
                     "Siren Control Mode used for selecting the mode to control a siren."
                     ::=  {  iMSwitchEntry 45  }

                  iMSwitchSendNormalMail OBJECT-TYPE
                     SYNTAX  INTEGER {
                        disable(0),
                        enable(1)
                     }
                     ACCESS  read-write
                     STATUS  mandatory
                     DESCRIPTION
                     "Enable sending email when sensor goes to normal"
                     ::=  {  iMSwitchEntry 46 }

                  iMSwitchSendTrap OBJECT-TYPE
                     SYNTAX  INTEGER {
                        disable(0),
                        enable(1)
                     }
                     ACCESS  read-write
                     STATUS  mandatory
                     DESCRIPTION
                     "Enable sending trap when sensor change status"
                     ::=  {  iMSwitchEntry 47 }

                  iMSwitchSendMail OBJECT-TYPE
                     SYNTAX  INTEGER {
                        disable(0),
                        enable(1)
                     }
                     ACCESS  read-write
                     STATUS  mandatory
                     DESCRIPTION
                     "Enable sending email when sensor change status"
                     ::=  {  iMSwitchEntry 48 }

               iMOtherSensor OBJECT IDENTIFIER ::= { iMEntry 19  }

                  iMVirtualAnalogSensor OBJECT IDENTIFIER ::= { iMOtherSensor 30  }

                     iMVirtualAnalogSensorNumber OBJECT-TYPE
                        SYNTAX INTEGER
                        ACCESS read-only
                        STATUS mandatory
                        DESCRIPTION
                        "The total number of VirtualAnalog Sensor port."
                        ::= {  iMVirtualAnalogSensor 1 }

                     iMVirtualAnalogSensorTable OBJECT-TYPE
                        SYNTAX  SEQUENCE OF IMVirtualAnalogSensorEntry
                        ACCESS  not-accessible
                        STATUS  mandatory
                        DESCRIPTION
                        "This table contains the data for every VirtualAnalog Sensor in the SensorArray. Each row in the table contains data for a different VirtualAnalog Sensor."
                        ::=  {  iMVirtualAnalogSensor 2   }

                        iMVirtualAnalogSensorEntry OBJECT-TYPE
                           SYNTAX  IMVirtualAnalogSensorEntry
                           ACCESS  not-accessible
                           STATUS  mandatory
                           DESCRIPTION
                           "This is an entry in the iMVirtualAnalogSensorEntry Table"
                           INDEX         { iMVirtualAnalogSensorIndex }
                           ::=  { iMVirtualAnalogSensorTable 1 }

                        IMVirtualAnalogSensorEntry ::= SEQUENCE {
                           iMVirtualAnalogSensorIndex
                              INTEGER,
                           iMVirtualAnalogDescription
                              DisplayString,
                           iMVirtualAnalogStatus
                              INTEGER,
                           iMVirtualAnalogOnline
                              INTEGER,
                           iMVirtualAnalogGoOnline
                              INTEGER,
                           iMVirtualAnalogHighWarning
                              INTEGER,
                           iMVirtualAnalogHighCritical
                              INTEGER,
                           iMVirtualAnalogLowWarning
                              INTEGER,
                           iMVirtualAnalogLowCritical
                              INTEGER,
                           iMVirtualAnalogRearm
                              INTEGER,
                           iMVirtualAnalogRaw
                              INTEGER,
                           iMVirtualAnalogEmailTrapLimit
                              INTEGER,
                           iMVirtualAnalogDelayError
                              INTEGER,
                           iMVirtualAnalogDelayNormal
                              INTEGER,
                           iMVirtualAnalogUnit
                              DisplayString,
                           iMVirtualAnalogAcknowledgement
                              INTEGER,
                           iMVirtualAnalogURL
                              DisplayString,
                           iMVirtualAnalogOpenURL
                              INTEGER,
                           iMVirtualAnalogContTimeHighCritical
                              INTEGER,
                           iMVirtualAnalogContTimeHighWarning
                              INTEGER,
                           iMVirtualAnalogContTimeNormal
                              INTEGER,
                           iMVirtualAnalogContTimeLowWarning
                              INTEGER,
                           iMVirtualAnalogContTimeLowCritical
                              INTEGER,
                           iMVirtualAnalogContTimeSensorError
                              INTEGER,
                           iMVirtualAnalogCalendar
                              INTEGER,
                           iMVirtualAnalogValueFactor
                              INTEGER
                        }

                          iMVirtualAnalogSensorIndex OBJECT-TYPE
                              SYNTAX  INTEGER (0..79)
                              ACCESS  read-only
                              STATUS  mandatory
                              DESCRIPTION
                              "A unique value for each VirtualAnalog sensor port."
                              ::=  {  iMVirtualAnalogSensorEntry 1   }

                          iMVirtualAnalogDescription OBJECT-TYPE
                              SYNTAX  DisplayString
                              ACCESS  read-write
                              STATUS  mandatory
                              DESCRIPTION
                              "A Description of this sensor"
                              ::=  {  iMVirtualAnalogSensorEntry 2   }

                           iMVirtualAnalogStatus OBJECT-TYPE
                              SYNTAX  INTEGER {
                                 noStatus(1),
                                 normal(2),
                                 highWarning(3),
                                 highCritical(4),
                                 lowWarning(5),
                                 lowCritical(6),
                                 sensorError(7)
                              }
                              ACCESS  read-only
                              STATUS  mandatory
                              DESCRIPTION
                              "The current status of this Sensor"
                              ::=  {  iMVirtualAnalogSensorEntry 4   }

                           iMVirtualAnalogOnline OBJECT-TYPE
                              SYNTAX  INTEGER {
                                 online(1),
                                 offline(2)
                              }
                              ACCESS  read-only
                              STATUS  mandatory
                              DESCRIPTION
                              "If this Sensor is currently online"
                                 ::=  {  iMVirtualAnalogSensorEntry 5   }

                           iMVirtualAnalogGoOnline OBJECT-TYPE
                              SYNTAX  INTEGER {
                                 goOnline(1),
                                 goOffline(2)
                              }
                              ACCESS  read-write
                              STATUS  mandatory
                              DESCRIPTION
                              "To put online enter a 1, to take offline enter a 2"
                              ::=  {  iMVirtualAnalogSensorEntry 6   }

                           iMVirtualAnalogHighWarning OBJECT-TYPE
                              SYNTAX  INTEGER
                              ACCESS  read-write
                              STATUS  mandatory
                              DESCRIPTION
                              "How high the relative VirtualAnalog this sensor measures before it sends a warning"
                              ::=  {  iMVirtualAnalogSensorEntry 7   }

                           iMVirtualAnalogHighCritical OBJECT-TYPE
                              SYNTAX  INTEGER
                              ACCESS  read-write
                              STATUS  mandatory
                              DESCRIPTION
                              "How high the relative VirtualAnalog this sensor measures before it becomes critical"
                              ::=  {  iMVirtualAnalogSensorEntry 8   }

                           iMVirtualAnalogLowWarning OBJECT-TYPE
                              SYNTAX  INTEGER
                              ACCESS  read-write
                              STATUS  mandatory
                              DESCRIPTION
                              "How low the relative VirtualAnalog this sensor measures before it sends a warning"
                              ::=  {  iMVirtualAnalogSensorEntry 9   }

                           iMVirtualAnalogLowCritical OBJECT-TYPE
                              SYNTAX  INTEGER
                              ACCESS  read-write
                              STATUS  mandatory
                              DESCRIPTION
                              "How low the relative VirtualAnalog this sensor measures before it becomes critical"
                              ::=  {  iMVirtualAnalogSensorEntry 10   }

                           iMVirtualAnalogRearm OBJECT-TYPE
                              SYNTAX  INTEGER
                              ACCESS  read-write
                              STATUS  mandatory
                              DESCRIPTION
                              "The percent relative VirtualAnalog to rearm the status. For example if status goes from normal to warning, the VirtualAnalog must go down iMAnalogueRearm below warning before the status goes to normal"
                              ::=  {  iMVirtualAnalogSensorEntry 11   }

                           iMVirtualAnalogRaw OBJECT-TYPE
                              SYNTAX  INTEGER 
                              ACCESS  read-only
                              STATUS  mandatory
                              DESCRIPTION
                              "The unformatted, raw, A/D value in this sensor. Contains more resolution than the formated percentage. This number can go from 0 to 1023 depending on the input voltage"
                              ::=  {  iMVirtualAnalogSensorEntry 13   }

                           iMVirtualAnalogEmailTrapLimit OBJECT-TYPE
                              SYNTAX  INTEGER {
                                disable(0),
                                enable(1)
                              }
                              ACCESS  read-write
                              STATUS  mandatory
                              DESCRIPTION
                              "Enable email/trap limit feature"
                              ::=  {  iMVirtualAnalogSensorEntry 17   }

                           iMVirtualAnalogDelayError OBJECT-TYPE
                              SYNTAX  INTEGER (0..65534)
                              ACCESS  read-write
                              STATUS  mandatory
                              DESCRIPTION
                              "Time in seconds after the sensor has been in error status before report as an error"
                              ::=  {  iMVirtualAnalogSensorEntry 21   }

                           iMVirtualAnalogDelayNormal OBJECT-TYPE
                              SYNTAX  INTEGER (0..65534)
                              ACCESS  read-write
                              STATUS  mandatory
                              DESCRIPTION
                              "Time in seconds after the sensor change from error to normal before report as normal"
                              ::=  {  iMVirtualAnalogSensorEntry 22   }

                           iMVirtualAnalogUnit OBJECT-TYPE
                              SYNTAX  DisplayString
                              ACCESS  read-write
                              STATUS  mandatory
                              DESCRIPTION
                              "Display unit in VirtualAnalog."
                              ::=  {  iMVirtualAnalogSensorEntry 27   }

                           iMVirtualAnalogAcknowledgement OBJECT-TYPE
                              SYNTAX INTEGER {
                                 ack(1)
                              }
                              ACCESS read-write
                              STATUS mandatory
                              DESCRIPTION
                              "Acknowledged sensor error and stop notification"
                              ::= {  iMVirtualAnalogSensorEntry 41 }

                           iMVirtualAnalogURL OBJECT-TYPE
                              SYNTAX DisplayString
                              ACCESS read-write
                              STATUS mandatory
                              DESCRIPTION
                              "Sensor URL link."
                              ::=  {  iMVirtualAnalogSensorEntry 43   }

                           iMVirtualAnalogOpenURL OBJECT-TYPE
                              SYNTAX INTEGER {
                                 cur-window(0),
                                 new-window(2)
                              }
                              ACCESS read-write
                              STATUS mandatory
                              DESCRIPTION
                              "Open URL in this browser or open in a new window."
                              ::=  {  iMVirtualAnalogSensorEntry 44   }

                           iMVirtualAnalogContTimeHighCritical OBJECT-TYPE
                              SYNTAX INTEGER (0..65535)
                              ACCESS read-write
                              STATUS mandatory
                              DESCRIPTION
                              "Continuous time for this sensor to be in High Critical before accepting new Status."
                              ::= {  iMVirtualAnalogSensorEntry 45 }

                           iMVirtualAnalogContTimeHighWarning OBJECT-TYPE
                              SYNTAX INTEGER (0..65535)
                              ACCESS read-write
                              STATUS mandatory
                              DESCRIPTION
                              "Continuous time for this sensor to be in High Warning before accepting new Status."
                              ::= {  iMVirtualAnalogSensorEntry 46 }

                           iMVirtualAnalogContTimeNormal OBJECT-TYPE
                              SYNTAX INTEGER (0..65535)
                              ACCESS read-write
                              STATUS mandatory
                              DESCRIPTION
                              "Continuous time for this sensor to be in Normal before accepting new Status."
                              ::= {  iMVirtualAnalogSensorEntry 47 }

                           iMVirtualAnalogContTimeLowWarning OBJECT-TYPE
                              SYNTAX INTEGER (0..65535)
                              ACCESS read-write
                              STATUS mandatory
                              DESCRIPTION
                              "Continuous time for this sensor to be in Low Warning before accepting new Status."
                              ::= {  iMVirtualAnalogSensorEntry 48 }

                           iMVirtualAnalogContTimeLowCritical OBJECT-TYPE
                              SYNTAX INTEGER (0..65535)
                              ACCESS read-write
                              STATUS mandatory
                              DESCRIPTION
                              "Continuous time for this sensor to be in Low Critical before accepting new Status."
                              ::= {  iMVirtualAnalogSensorEntry 49 }

                           iMVirtualAnalogContTimeSensorError OBJECT-TYPE
                              SYNTAX INTEGER (0..65535)
                              ACCESS read-write
                              STATUS mandatory
                              DESCRIPTION
                              "Continuous time for this sensor to be in Sensor Error before accepting new Status."
                              ::= {  iMVirtualAnalogSensorEntry 50 }

                           iMVirtualAnalogCalendar OBJECT-TYPE
                              SYNTAX INTEGER {
                                disable(0),
                                enable(1)
                              }
                              ACCESS read-write
                              STATUS mandatory
                              DESCRIPTION
                              "Enable or disable the calendar filtering working hours of sensor."
                              ::= {  iMVirtualAnalogSensorEntry 51 }

                           iMVirtualAnalogValueFactor OBJECT-TYPE
                              SYNTAX INTEGER {
                                 x1(1),
                                 x0-1(10),
                                 x0-01(100),
                                 x0-001(1000)
                              }
                              ACCESS read-write
                              STATUS mandatory
                              DESCRIPTION
                              "To change the ratio of value."
                              ::= {  iMVirtualAnalogSensorEntry 52 }

                  iMVirtualSwitchSensor OBJECT IDENTIFIER ::= { iMOtherSensor 31  }

                     iMVirtualSwitchSensorNumber OBJECT-TYPE
                        SYNTAX INTEGER
                        ACCESS read-only
                        STATUS mandatory
                        DESCRIPTION
                        "The total number of VirtualSwitch Sensor port."
                        ::= {  iMVirtualSwitchSensor 1 }

                     iMVirtualSwitchSensorTable OBJECT-TYPE
                        SYNTAX  SEQUENCE OF IMVirtualSwitchSensorEntry
                        ACCESS  not-accessible
                        STATUS  mandatory
                        DESCRIPTION
                        "This table contains the data for every VirtualSwitch Sensor in the SensorArray. Each row in the table contains data for a different VirtualSwitch Sensor."
                        ::=  {  iMVirtualSwitchSensor 2   }

                        iMVirtualSwitchSensorEntry OBJECT-TYPE
                           SYNTAX  IMVirtualSwitchSensorEntry
                           ACCESS  not-accessible
                           STATUS  mandatory
                           DESCRIPTION
                           "This is an entry in the iMVirtualSwitchSensorEntry Table"
                           INDEX         { iMVirtualSwitchSensorIndex }
                           ::=  { iMVirtualSwitchSensorTable 1 }

                        IMVirtualSwitchSensorEntry ::= SEQUENCE {
                           iMVirtualSwitchSensorIndex
                              INTEGER,
                           iMVirtualSwitchDescription
                              DisplayString,
                           iMVirtualSwitchStatus
                              INTEGER,
                           iMVirtualSwitchOnline
                              INTEGER,
                           iMVirtualSwitchGoOnline
                              INTEGER,
                           iMVirtualSwitchEmailTrapLimit
                              INTEGER,
                           iMVirtualSwitchContTimeHighCritical
                              INTEGER,
                           iMVirtualSwitchContTimeNormal
                              INTEGER,
                           iMVirtualSwitchDescriptionCritical
                              DisplayString,
                           iMVirtualSwitchDescriptionNormal
                              DisplayString,                           
                           iMVirtualSwitchAcknowledgement
                              INTEGER,
                           iMVirtualSwitchURL
                              DisplayString,
                           iMVirtualSwitchOpenURL
                              INTEGER,
                           iMVirtualSwitchCalendar
                              INTEGER,
                           iMVirtualSwitchNormalState
                              INTEGER
                        }

                          iMVirtualSwitchSensorIndex OBJECT-TYPE
                              SYNTAX  INTEGER (0..79)
                              ACCESS  read-only
                              STATUS  mandatory
                              DESCRIPTION
                              "A unique value for each VirtualSwitch sensor port."
                              ::=  {  iMVirtualSwitchSensorEntry 1   }

                          iMVirtualSwitchDescription OBJECT-TYPE
                              SYNTAX  DisplayString
                              ACCESS  read-write
                              STATUS  mandatory
                              DESCRIPTION
                              "A Description of this sensor"
                              ::=  {  iMVirtualSwitchSensorEntry 2   }

                           iMVirtualSwitchStatus OBJECT-TYPE
                              SYNTAX  INTEGER {
                                 noStatus(1),
                                 normal(2),
                                 highWarning(3),
                                 highCritical(4),
                                 lowWarning(5),
                                 lowCritical(6),
                                 sensorError(7)
                              }
                              ACCESS  read-only
                              STATUS  mandatory
                              DESCRIPTION
                              "The current status of this Sensor"
                              ::=  {  iMVirtualSwitchSensorEntry 4   }

                           iMVirtualSwitchOnline OBJECT-TYPE
                              SYNTAX  INTEGER {
                                 online(1),
                                 offline(2)
                              }
                              ACCESS  read-only
                              STATUS  mandatory
                              DESCRIPTION
                              "If this Sensor is currently online"
                                 ::=  {  iMVirtualSwitchSensorEntry 5   }

                           iMVirtualSwitchGoOnline OBJECT-TYPE
                              SYNTAX  INTEGER {
                                 goOnline(1),
                                 goOffline(2)
                              }
                              ACCESS  read-write
                              STATUS  mandatory
                              DESCRIPTION
                              "To put online enter a 1, to take offline enter a 2"
                              ::=  {  iMVirtualSwitchSensorEntry 6   }

                           iMVirtualSwitchEmailTrapLimit OBJECT-TYPE
                              SYNTAX  INTEGER {
                                disable(0),
                                enable(1)
                              }
                              ACCESS  read-write
                              STATUS  mandatory
                              DESCRIPTION
                              "Enable email/trap limit feature"
                              ::=  {  iMVirtualSwitchSensorEntry 17   }

                           iMVirtualSwitchContTimeHighCritical OBJECT-TYPE
                              SYNTAX  INTEGER (0..65534)
                              ACCESS  read-write
                              STATUS  mandatory
                              DESCRIPTION
                              "Continuous time for this sensor to be in High Critical before accepting new Status."
                              ::=  {  iMVirtualSwitchSensorEntry 21   }

                           iMVirtualSwitchContTimeNormal OBJECT-TYPE
                              SYNTAX INTEGER (0..65535)
                              ACCESS read-write
                              STATUS mandatory
                              DESCRIPTION
                              "Continuous time for this sensor to be in Normal before accepting new Status."
                              ::=  {  iMVirtualSwitchSensorEntry 22   }

                           iMVirtualSwitchDescriptionCritical OBJECT-TYPE
                              SYNTAX DisplayString
                              ACCESS read-write
                              STATUS mandatory
                              DESCRIPTION
                              "Description of status when the virsual switch is critical"
                              ::=  {  iMVirtualSwitchSensorEntry 26   }

                           iMVirtualSwitchDescriptionNormal OBJECT-TYPE
                              SYNTAX DisplayString
                              ACCESS read-write
                              STATUS mandatory
                              DESCRIPTION
                              "Description of status when the virsual switch is normal"
                              ::=  {  iMVirtualSwitchSensorEntry 27   }

                           iMVirtualSwitchAcknowledgement OBJECT-TYPE
                              SYNTAX INTEGER {
                                 ack(1)
                              }
                              ACCESS read-write
                              STATUS mandatory
                              DESCRIPTION
                              "Acknowledged sensor error and stop notification"
                              ::= {  iMVirtualSwitchSensorEntry 41 }

                           iMVirtualSwitchURL OBJECT-TYPE
                              SYNTAX DisplayString
                              ACCESS read-write
                              STATUS mandatory
                              DESCRIPTION
                              "Sensor URL link."
                              ::=  {  iMVirtualSwitchSensorEntry 43   }

                           iMVirtualSwitchOpenURL OBJECT-TYPE
                              SYNTAX INTEGER {
                                 cur-window(0),
                                 new-window(2)
                              }
                              ACCESS read-write
                              STATUS mandatory
                              DESCRIPTION
                              "Open URL in this browser or open in a new window."
                              ::=  {  iMVirtualSwitchSensorEntry 44   }

                           iMVirtualSwitchCalendar OBJECT-TYPE
                              SYNTAX INTEGER {
                                disable(0),
                                enable(1)
                              }
                              ACCESS read-write
                              STATUS mandatory
                              DESCRIPTION
                              "Enable or disable the calendar filtering working hours of sensor."
                              ::= {  iMVirtualSwitchSensorEntry 45 }

                           iMVirtualSwitchNormalState OBJECT-TYPE
                              SYNTAX INTEGER
                              ACCESS read-write
                              STATUS mandatory
                              DESCRIPTION
                              "The normal state of a return of the virsual switch. If a return of the virsual switch is equal this normal state value, it is normal. Otherwise, it is critical."
                              ::= {  iMVirtualSwitchSensorEntry 46 }

               iMDebug OBJECT-TYPE
                  SYNTAX  INTEGER {
                     off(0),
                     on(1)                     
                  }
                  ACCESS  read-write
                  STATUS  mandatory
                  DESCRIPTION
                  "SP only: Turn on or off debug messages"
                  ::=  {  iMEntry 20  }

               iMTrapResend OBJECT-TYPE
                  SYNTAX  INTEGER {
                      off(0),
                      on(1)
                  }
                  ACCESS  read-write
                  STATUS  mandatory
                  DESCRIPTION
                  "If traps for Warning or Error should be resent. Traps for Normal status are sent once"
                  ::=  {  iMEntry 22  }

               iMTrapResendInterval OBJECT-TYPE
                  SYNTAX  INTEGER
                  ACCESS  read-write
                  STATUS  mandatory
                  DESCRIPTION
                  "How often to resend mail or Traps. Enter the number of seconds from 15 to 65535. Mail for WARNING and ERROR are resent at this interval. Traps for Normal status are sent once"
                  ::=  {  iMEntry 23  }

               iMSendTraps OBJECT-TYPE
                  SYNTAX  INTEGER {
                     on(1),
                     off(2)
                  }
                  ACCESS  read-write
                  STATUS  mandatory
                  DESCRIPTION
                  "Turn on or off the sending of traps"
                  ::=  {  iMEntry 24  }

               iMTrapDestination OBJECT-TYPE
                  SYNTAX  IpAddress
                  ACCESS  read-write
                  STATUS  mandatory
                  DESCRIPTION
                  "The IP address of the trap destination"
                  ::=  {  iMEntry 25  }

               iMTrapCommunity OBJECT-TYPE
                  SYNTAX  DisplayString
                  ACCESS  read-write
                  STATUS  mandatory
                  DESCRIPTION
                  "The community string of the trap destination"
                  ::=  {  iMEntry 26  }

               iMDefaultGateway OBJECT-TYPE
                  SYNTAX  IpAddress
                  ACCESS  read-write
                  STATUS  mandatory
                  DESCRIPTION
                  "If the destination is on another network, enter the IP address of the router"
                  ::=  {  iMEntry 27  }

               iMSubnetMask OBJECT-TYPE
                  SYNTAX  IpAddress
                  ACCESS  read-write
                  STATUS  mandatory
                  DESCRIPTION
                  "If the trap destination uses the default gateway"
                  ::=  {  iMEntry 28  }

               iMRouteAdd OBJECT-TYPE
                  SYNTAX  DisplayString
                  ACCESS  read-write
                  STATUS  mandatory
                  DESCRIPTION
                  "SP only: Up to 4, Manual additions to the routing table in the form, Network IP Address, Netmask, Gateway IP address"
                  ::=  {  iMEntry 29  }


               iMSendMail OBJECT-TYPE
                  SYNTAX  INTEGER {
                     on(1),
                     off(2)
                  }
                  ACCESS  read-write
                  STATUS  mandatory
                  DESCRIPTION
                  "Turn on or off the sending of Mail"
                  ::=  {  iMEntry 30  }

               iMMailRecpt OBJECT-TYPE
                  SYNTAX  DisplayString
                  ACCESS  read-write
                  STATUS  mandatory
                  DESCRIPTION
                  "The email address of the Recipient"
                  ::=  {  iMEntry 31  }

               iMMailFrom OBJECT-TYPE
                  SYNTAX  DisplayString
                  ACCESS  read-write
                  STATUS  mandatory
                  DESCRIPTION
                  "The email address of the Sender"
                  ::=  {  iMEntry 32  }

               iMMailSMTP OBJECT-TYPE
                  SYNTAX  DisplayString
                  ACCESS  read-write
                  STATUS  mandatory
                  DESCRIPTION
                  "The Address of the SMTP server"
                  ::=  {  iMEntry 33  }

               iMMailJpgInline OBJECT-TYPE
                  SYNTAX  INTEGER {
                     inline(1),
                     link(2)
                  }
                  ACCESS  read-write
                  STATUS  mandatory
                  DESCRIPTION
                  "If the jpg for this event is sent as an http link or is included with mail as an attachment"
                  ::=  {  iMEntry 34  }

               iMMailResendInterval OBJECT-TYPE
                  SYNTAX  INTEGER
                  ACCESS  read-write
                  STATUS  mandatory
                  DESCRIPTION
                  "How often to resend mail or Traps. Enter the number of seconds from 10 to 60. Mail for WARNING and ERROR are resent at this interval. Mail for Normal status are sent once"
                  ::=  {  iMEntry 36  }

               iMMailMaxResend OBJECT-TYPE
                  SYNTAX  INTEGER
                  ACCESS  read-write
                  STATUS  mandatory
                  DESCRIPTION
                  "The maximum number of times to resend mail. If set to 0 only send once. The maximum value is 5"
                  ::=  {  iMEntry 37  }

               iMMailLastStatus OBJECT-TYPE
                  SYNTAX  DisplayString
                  ACCESS  read-only
                  STATUS  mandatory
                  DESCRIPTION
                  "The status of the most recent attempt to send an email"
                  ::=  {  iMEntry 39  }

               iMSupportMailRcpt OBJECT-TYPE
                  SYNTAX  DisplayString
                  ACCESS  read-write
                  STATUS  mandatory
                  DESCRIPTION
                  "SP8L only: E-Mail address of support"
                  ::=  {  iMEntry 40  }

               iMTrapMailPollInterval OBJECT-TYPE
                  SYNTAX  INTEGER
                  ACCESS  read-write
                  STATUS  mandatory
                  DESCRIPTION
                  "SP Only: How often the sensor thresholds are tested before sending traps or mail. This can vary from 3 to 15 seconds"
                  ::=  {  iMEntry 50  }

               iMSendTestMail OBJECT-TYPE
                  SYNTAX  INTEGER
                  ACCESS  read-write
                  STATUS  mandatory
                  DESCRIPTION
                  "Send out an email test message"
                  ::=  {  iMEntry 51  }

               iMLastSystemError OBJECT-TYPE
                  SYNTAX  DisplayString
                  ACCESS  read-only
                  STATUS  mandatory
                  DESCRIPTION
                  "A text string containing the description of the last system error"
                  ::=  {  iMEntry 52  }

               iMDataCollectionPeriod OBJECT-TYPE
                  SYNTAX  INTEGER
                  ACCESS  read-write
                  STATUS  mandatory
                  DESCRIPTION
                  "The number of minutes between collections of the data logger. This can vary from 1 to 60 minutes"
                  ::=  {  iMEntry 53  }

               iMMailTimeout OBJECT-TYPE
                  SYNTAX  INTEGER
                  ACCESS  read-write
                  STATUS  mandatory
                  DESCRIPTION
                  "The number of seconds to wait for a timeout while sending email This can vary from 10 to 30 seconds"
                  ::=  {  iMEntry 54  }

               iMAutoSense OBJECT-TYPE
                  SYNTAX  INTEGER {
                        disable(0),
                        enable(1)
                  }                  
                  ACCESS  read-write
                  STATUS  mandatory
                  DESCRIPTION
                  "Enable Auto-sense feature"
                  ::=  {  iMEntry 55  }

               iMChecksum OBJECT-TYPE
                  SYNTAX  INTEGER
                  ACCESS  read-only
                  STATUS  mandatory
                  DESCRIPTION
                  "SP Only: The Flash Checksum, computed dynamically whenever this object is read"
                  ::=  {  iMEntry 56  }

               iMUsePassword OBJECT-TYPE
                  SYNTAX  INTEGER {
                     usePassword(0),
                     doNotUsePassword(1)
                  }
                  ACCESS  read-write
                  STATUS  mandatory
                  DESCRIPTION
                  "Determines whether or not the set and get community are used to check for access rights"
                  ::=  {  iMEntry 57  }

               iMDisplayLogo OBJECT-TYPE
                  SYNTAX  INTEGER {
                        disable(0),
                        enable(1)
                  }                  
                  ACCESS  read-write
                  STATUS  mandatory
                  DESCRIPTION
                  "Enable or Disable the display of the logo"
                  ::=  {  iMEntry 59  }

               iMTrapType OBJECT-TYPE
                  SYNTAX  INTEGER {
                     specificTypeTrap(1),
                     generalTypeTrap(2),
                     bothTypeTraps(3),
                     statusTypeTraps(4)
                  }                  
                  ACCESS  read-write
                  STATUS  mandatory
                  DESCRIPTION
                  "Whether to generate a trap that covers all sensors, a specific trap for each sensor, or both types of traps"
                  ::=  {  iMEntry 60  }

               iMMailCC OBJECT-TYPE
                  SYNTAX  DisplayString
                  ACCESS  read-write
                  STATUS  mandatory
                  DESCRIPTION
                  "The email address of the CC"
                  ::=  {  iMEntry 61  }

               iMAllowIPChange OBJECT-TYPE
                SYNTAX  INTEGER {
                    enable(1),
                    disable(2)
                  }
                  ACCESS  read-write
                  STATUS  mandatory
                  DESCRIPTION
                  "This disables the changing of the IP address. The default is to enable changing the IP address"
                  ::=  {  iMEntry 62  }

               iMTimeOfDay OBJECT-TYPE
                  SYNTAX  DisplayString
                  ACCESS  read-write
                  STATUS  mandatory
                  DESCRIPTION
                  "The time of day in the format day/month/year hour(1-24):minutes:seconds for example 23/10/02 12:45:06"
                  ::=  {  iMEntry 65  }

               iMEnableSysLog OBJECT-TYPE
                SYNTAX  INTEGER {
                     enableLogToFlash(1),
                     enableLogToNetAndFlash(2),
                     disable(3)
                  }                  
                  ACCESS  read-write
                  STATUS  mandatory
                  DESCRIPTION
                  "This enables sysLog Messages,including logging to the Net. The Destination IP of the net messages is the same as the source IP of the sender of this command"
                  ::=  {  iMEntry 66  }

               iMReadSysLog OBJECT-TYPE
                  SYNTAX  INTEGER {
                     lastMessage(1),
                     allMessages(2)
                  }                  
                  ACCESS  read-write
                  STATUS  mandatory
                  DESCRIPTION
                  "Return the sysLog Message in the snmp PDU and if enableLogToNetAndFlash in iMEnableSysLog, also send in debug message format, A Write of a 2 will return all of the messages in debug format"
                  ::=  {  iMEntry 67  }

               iMClearSysLog OBJECT-TYPE
                  SYNTAX  INTEGER {
                     allMessages(2)
                  }                  
                  ACCESS  read-write
                  STATUS  mandatory
                  DESCRIPTION
                  "Delete all entries in the sys log"
                  ::=  {  iMEntry 68  }

               iMSyslogDestIP OBJECT-TYPE
                  SYNTAX  IpAddress
                  ACCESS  read-write
                  STATUS  mandatory
                  DESCRIPTION
                  "The IP Address of the Syslog server. Note: This must be in dotted decimal form"
                  ::=  {  iMEntry 69  }

               iMSyslogPort OBJECT-TYPE
                  SYNTAX  Gauge 
                  ACCESS  read-write
                  STATUS  mandatory
                  DESCRIPTION
                  "The Port Number of the Syslog server."
                  ::=  {  iMEntry 70  }

               iMSetSyslogMsgPrefix OBJECT-TYPE
                  SYNTAX  DisplayString
                  ACCESS  read-write
                  STATUS  mandatory
                  DESCRIPTION
                  "SP Only: The Prefix message of the Syslog message"
                  ::=  {  iMEntry 71  }

--
-- iMEntry 72 is reserved for iMLanFullDuplex ( SP Only )
--

--
-- iMEntry 73 is reserved for iMExpectedMicrocodeCRC ( SP Only )
--

--
-- iMEntry 74 is reserved for iMExpectedMicrocodeLength ( SP Only )
--

--
-- iMEntry 75 is reserved for iMActualMicrocodeCRC ( SP Only )
--

--
-- iMEntry 76 is reserved for iMExpectedBootCRC ( SP Only )
--

--
-- iMEntry 77 is reserved for iMActualBootCRC ( SP Only )
--

--
-- iMEntry 78 is reserved for iMBootVersion ( SP Only )
--

--
-- iMEntry 80 is reserved for iMAdcCalibrate
--

               iMTimeZone OBJECT-TYPE
                  SYNTAX  INTEGER  
                  ACCESS  read-write
                  STATUS  mandatory
                  DESCRIPTION
                  "System time zone" 
                  ::=  {  iMEntry 81  }

--
-- iMEntry 82 is reserved for iMExtraDryContactEnable ( SP Only )
--

               iMMegaVersion OBJECT-TYPE
                  SYNTAX  INTEGER
                  ACCESS  read-only
                  STATUS  mandatory
                  DESCRIPTION
                  "Version number of mega board"
                  ::=  {  iMEntry 83  }

               iMNtpMode OBJECT-TYPE
                  SYNTAX  INTEGER {
                     notUse(0),
                     oneTime(1),
                     onSystemStartUp(2),
                     onceAMounth(3),
                     onceAWeek(4),
                     onceADay(5),
                     onceAnHour(6),
                     continuous(7)
                  }
                  ACCESS  read-write
                  STATUS  mandatory
                  DESCRIPTION
                  "Mode to synchronous with ntp server" 
                  ::=  {  iMEntry 84  }

               iMNtpServer OBJECT-TYPE
                  SYNTAX  DisplayString
                  ACCESS  read-write
                  STATUS  mandatory
                  DESCRIPTION
                  "NTP server which this machine synchronous with"
                  ::=  {  iMEntry 85  }

--
-- iMEntry 86 is reserved for iMModel string which is used internaly (Jacarta).
--

               iMSMTPAuth OBJECT-TYPE
                  SYNTAX  INTEGER {
                     enable(1),
                     disable(2)
                  }                  
                  ACCESS  read-write
                  STATUS  mandatory
                  DESCRIPTION
                  "This enables the SMTP authentication"
                  ::=  {  iMEntry 87  }

               iMSMTPLogin OBJECT-TYPE
                  SYNTAX  DisplayString
                  ACCESS  read-write
                  STATUS  mandatory
                  DESCRIPTION
                  "The username used to login into SMTP server"
                  ::=  {  iMEntry 88  }

               iMSMTPPassword OBJECT-TYPE
                  SYNTAX  DisplayString
                  ACCESS  read-write
                  STATUS  mandatory
                  DESCRIPTION
                  "The password used to login into SMTP server"
                  ::=  {  iMEntry 89  }

               iMDNSServer OBJECT-TYPE
                  SYNTAX  IpAddress
                  ACCESS  read-write
                  STATUS  mandatory
                  DESCRIPTION
                  "IP address of the DNS server"
                  ::=  {  iMEntry 90  }

               iMAltWebPort OBJECT-TYPE
                  SYNTAX  Gauge
                  ACCESS  read-write
                  STATUS  mandatory
                  DESCRIPTION
                  "The alternative for a port number 80 used to access the web interface"
                  ::=  {  iMEntry 91  }

               iMNumberOfSensorPort OBJECT-TYPE
                  SYNTAX  INTEGER
                  ACCESS  read-only
                  STATUS  mandatory
                  DESCRIPTION
                  "The number of sensor ports(regardless of their current state)"
                  ::=  {  iMEntry 92  }
               
               iMSendTrapsAlive OBJECT-TYPE
                  SYNTAX  INTEGER {
                     on(1),
                     off(2)
                  }
                  ACCESS  read-write
                  STATUS  mandatory
                  DESCRIPTION
                  "On or off send keep alive traps."
                  ::=  {  iMEntry 93  }
               
               iMTrapReIntervalAlive OBJECT-TYPE
                  SYNTAX  INTEGER
                  ACCESS  read-write
                  STATUS  mandatory
                  DESCRIPTION
                  "Time between each keep alive trap."
                  ::=  {  iMEntry 94  }
               
               iMUseCamera OBJECT-TYPE
                  SYNTAX  INTEGER {
                     off(0),
                     on(1)
                  }
                  ACCESS  read-write
                  STATUS  mandatory
                  DESCRIPTION
                  "On or off camera."
                  ::=  {  iMEntry 95  }
                                 
               iMAdcCalibratePort OBJECT-TYPE
                  SYNTAX  INTEGER
                  ACCESS  read-write
                  STATUS  mandatory
                  DESCRIPTION
                  "Calibrate value for analog sensor."
                  ::=  {  iMEntry 96  }

--
-- iMEntry 97 is reseverd for future using with Linux version (Jacarta).
--

               iMMailSubject OBJECT-TYPE
                  SYNTAX  DisplayString
                  ACCESS  read-write
                  STATUS  mandatory
                  DESCRIPTION
                  "Email Subject."
                  ::=  {  iMEntry 98  }

          iMSnmpPort OBJECT-TYPE
                  SYNTAX  Gauge 
                  ACCESS  read-write
                  STATUS  mandatory
                  DESCRIPTION
                  "SP Only: Port number used to access snmp"
                  ::=  {  iMEntry 99  }

          iMSnmpTrapPort OBJECT-TYPE
                  SYNTAX  Gauge 
                  ACCESS  read-write
                  STATUS  mandatory
                  DESCRIPTION
                  "SP Only: Port number used to access trap snmp"
                  ::=  {  iMEntry 100  }

          iMSnmpIndexingMode OBJECT-TYPE
                  SYNTAX  INTEGER {
                     index0(0),
                     index1(1)
                  }
                  ACCESS  read-write
                  STATUS  mandatory
                  DESCRIPTION
                  "CP8 Only: Snmp table index starting from 0 or 1 "
                  ::=  {  iMEntry 101  }

--
-- iMEntry 102 is reserved for iMSensorSummary
--
               iMNotifyBoot OBJECT-TYPE
                  SYNTAX  INTEGER
                  ACCESS  read-write
                  STATUS  mandatory
                  DESCRIPTION
                  "SP2 Only: Enable Notify on boot up"
                  ::=  {  iMEntry 103  }

               iMDelayNotifyBoot OBJECT-TYPE
                  SYNTAX  INTEGER
                  ACCESS  read-write
                  STATUS  mandatory
                  DESCRIPTION
                  "SP2 Only: Delay time for boot up notify"
                  ::=  {  iMEntry 104  }

               iMSmtpPort OBJECT-TYPE
                  SYNTAX  INTEGER
                  ACCESS  read-write
                  STATUS  mandatory
                  DESCRIPTION
                  "SMTP Port number used to send email"
                  ::=  {  iMEntry 105  }

               iMReboot OBJECT-TYPE
                  SYNTAX  INTEGER
                  ACCESS  read-write
                  STATUS  mandatory
                  DESCRIPTION
                  "Reboot SP2/SP8 set to 1"
                  ::=  {  iMEntry 106  }

          iMServerEnable OBJECT-TYPE
                  SYNTAX  INTEGER {
                        disable(0),
                        enable(1)
                  }
                  ACCESS  read-write
                  STATUS  mandatory
                  DESCRIPTION
                  "Enable database changed notify feature"
                  ::=  {  iMEntry 107  }

          iMFirmwareVersion OBJECT-TYPE
                  SYNTAX  DisplayString
                  ACCESS  read-only
                  STATUS  mandatory
                  DESCRIPTION
                  "Current firmware version"
                  ::=  {  iMEntry 108  }

          iMProductType OBJECT-TYPE
                  SYNTAX  INTEGER {
                     iM2(1),
                     iM8(2),
                     iMLinuxWithoutUSB(3),
                     iMLinuxWithUSB(4),
                     iMeter(5)
                  }
                  ACCESS  read-only
                  STATUS  mandatory
                  DESCRIPTION
                  "Product type"
                  ::=  {  iMEntry 109  }

               iMRequestResendTrap OBJECT-TYPE
                  SYNTAX  INTEGER
                  ACCESS  read-write
                  STATUS  mandatory
                  DESCRIPTION
                  "SP only: Send immediately all traps by set to 1"
                  ::=  {  iMEntry 110  }

--
-- iMEntry 111 is reserved for Server Project
--

               iMSeparateEmail OBJECT-TYPE
                  SYNTAX  INTEGER {
                     notSeparate(0),
                     separate(1)
                  }
                  ACCESS  read-write
                  STATUS  mandatory
                  DESCRIPTION
                  "SP only: Separate Email by set 1 for not Separate Email set 0"
                  ::=  {  iMEntry 112  }

               iMMailCustom OBJECT-TYPE
                  SYNTAX  INTEGER {
                     normal(0),
                     custom(1)
                  }
                  ACCESS  read-write
                  STATUS  mandatory
                  DESCRIPTION
                  "SP only: Custom mail is removed 'http://' in the mail footer"
                  ::=  {  iMEntry 113  }

          iMUntidePassword OBJECT-TYPE
                  SYNTAX  INTEGER {
                     tidePassword(0),
                     untidePassword(1)
                  }
                  ACCESS  read-write
                  STATUS  mandatory
                  DESCRIPTION
                  "Use web password as SNMP password"
                  ::=  {  iMEntry 114  }

          iMWebPassword OBJECT IDENTIFIER ::= { iMEntry 115  }
              iMWebAdminPassword OBJECT-TYPE
                  SYNTAX DisplayString
                  ACCESS read-write
                  STATUS mandatory
                  DESCRIPTION
                  "Password Admin for login web and other connections"
                  ::= {  iMWebPassword 1 }

              iMWebUserPassword OBJECT-TYPE
                  SYNTAX DisplayString
                  ACCESS read-write
                  STATUS mandatory
                  DESCRIPTION
                  "Password User for login web and other connections"
                  ::= {  iMWebPassword 2 }

          iMReloadNetwork OBJECT-TYPE
                  SYNTAX  INTEGER {
                     reload(1)
                  }
                  ACCESS  read-write
                  STATUS  mandatory
                  DESCRIPTION
                  "Set 1 for reload network seting"
                  ::=  {  iMEntry 116  }

          iMStatusNumber OBJECT IDENTIFIER ::= { iMEntry 117  }
              iMStatusNumberNotNormal OBJECT-TYPE
                  SYNTAX INTEGER
                  ACCESS read-only
                  STATUS mandatory
                  DESCRIPTION
                  "Number of sensor status is Warning, Critical and Sensor Error"
                  ::= {  iMStatusNumber 1 }

              iMStatusNumberCriticalAndError OBJECT-TYPE
                  SYNTAX INTEGER
                  ACCESS read-only
                  STATUS mandatory
                  DESCRIPTION
                  "Number of sensor status is Critical and Sensor Error"
                  ::= {  iMStatusNumber 2 }

              iMStatusNumberError OBJECT-TYPE
                  SYNTAX INTEGER
                  ACCESS read-only
                  STATUS mandatory
                  DESCRIPTION
                  "Number of sensor status is Sensor Error"
                  ::= {  iMStatusNumber 3 }
                  
          iMTypeName OBJECT IDENTIFIER ::= { iMEntry 118  }
              iMTypeTemperatureName OBJECT-TYPE
                  SYNTAX DisplayString
                  ACCESS read-write
                  STATUS mandatory
                  DESCRIPTION
                  "A Description of Sensor Type Name on web interface"
                  ::= {  iMTypeName 1 }

              iMTypeSHT11Name OBJECT-TYPE
                  SYNTAX DisplayString
                  ACCESS read-write
                  STATUS mandatory
                  DESCRIPTION
                  "A Description of Sensor Type Name on web interface"
                  ::= {  iMTypeName 135 }

              iMTypeSHT11HumidityName OBJECT-TYPE
                  SYNTAX DisplayString
                  ACCESS read-write
                  STATUS mandatory
                  DESCRIPTION
                  "A Description of Sensor Type Name on web interface"
                  ::= {  iMTypeName 2 }
                  
              iMTypeSHT11TempName OBJECT-TYPE
                  SYNTAX DisplayString
                  ACCESS read-write
                  STATUS mandatory
                  DESCRIPTION
                  "A Description of Sensor Type Name on web interface"
                  ::= {  iMTypeName 3 }
           
              iMTypeIntelliVoltName OBJECT-TYPE
                  SYNTAX DisplayString
                  ACCESS read-write
                  STATUS mandatory
                  DESCRIPTION
                  "A Description of Sensor Type Name on web interface"
                  ::= {  iMTypeName 4 }

              iMTypeIntelliAmpName OBJECT-TYPE
                  SYNTAX DisplayString
                  ACCESS read-write
                  STATUS mandatory
                  DESCRIPTION
                  "A Description of Sensor Type Name on web interface"
                  ::= {  iMTypeName 5 }
                  
              iMTypeAirflowName OBJECT-TYPE
                  SYNTAX DisplayString
                  ACCESS read-write
                  STATUS mandatory
                  DESCRIPTION
                  "A Description of Sensor Type Name on web interface"
                  ::= {  iMTypeName 6 }
                  
              iMTypeDrycontactInoutName OBJECT-TYPE
                  SYNTAX DisplayString
                  ACCESS read-write
                  STATUS mandatory
                  DESCRIPTION
                  "A Description of Sensor Type Name on web interface"
                  ::= {  iMTypeName 7 }

              iMTypeDrycontactInputName OBJECT-TYPE
                  SYNTAX DisplayString
                  ACCESS read-write
                  STATUS mandatory
                  DESCRIPTION
                  "A Description of Sensor Type Name on web interface"
                  ::= {  iMTypeName 8 }
                     
              iMTypeWaterName OBJECT-TYPE
                  SYNTAX DisplayString
                  ACCESS read-write
                  STATUS mandatory
                  DESCRIPTION
                  "A Description of Sensor Type Name on web interface"
                  ::= {  iMTypeName 10 }

              iMTypeSecurityName OBJECT-TYPE
                  SYNTAX DisplayString
                  ACCESS read-write
                  STATUS mandatory
                  DESCRIPTION
                  "A Description of Sensor Type Name on web interface"
                  ::= {  iMTypeName 11 }
                  
              iMTypeSirenName OBJECT-TYPE
                  SYNTAX DisplayString
                  ACCESS read-write
                  STATUS mandatory
                  DESCRIPTION
                  "A Description of Sensor Type Name on web interface"
                  ::= {  iMTypeName 12 }
                  
              iMTypeRelayName OBJECT-TYPE
                  SYNTAX DisplayString
                  ACCESS read-write
                  STATUS mandatory
                  DESCRIPTION
                  "A Description of Sensor Type Name on web interface"
                  ::= {  iMTypeName 13 }

              iMTypeACvoltageName OBJECT-TYPE
                  SYNTAX DisplayString
                  ACCESS read-write
                  STATUS mandatory
                  DESCRIPTION
                  "A Description of Sensor Type Name on web interface"
                  ::= {  iMTypeName 14 }
                                                                                      
              iMTypeSmokeName OBJECT-TYPE
                  SYNTAX DisplayString
                  ACCESS read-write
                  STATUS mandatory
                  DESCRIPTION
                  "A Description of Sensor Type Name on web interface"
                  ::= {  iMTypeName  21 }
                  
              iMTypeThermostatName OBJECT-TYPE
                  SYNTAX DisplayString
                  ACCESS read-write
                  STATUS mandatory
                  DESCRIPTION
                  "A Description of Sensor Type Name on web interface"
                  ::= {  iMTypeName  128 }

              iMTypeVirtualName OBJECT-TYPE
                  SYNTAX DisplayString
                  ACCESS read-write
                  STATUS mandatory
                  DESCRIPTION
                  "A Description of Sensor Type Name on web interface"
                  ::= {  iMTypeName  129 }

                  
   iMeter OBJECT IDENTIFIER ::= { jacarta 2 }

      iMeterSummary OBJECT IDENTIFIER  ::=  {  iMeter 1 }

      iMeterDevice OBJECT IDENTIFIER  ::=  {  iMeter 2 }

         deviceTable OBJECT-TYPE
            SYNTAX  SEQUENCE OF DeviceEntry
            ACCESS  not-accessible
            STATUS  mandatory
            DESCRIPTION
            "This table contains the property for every plugged-in device."
            ::=  {  iMeterDevice 1   }

         deviceEntry OBJECT-TYPE
            SYNTAX  DeviceEntry
            ACCESS  not-accessible
            STATUS  mandatory
            DESCRIPTION
            "This is an entry in the deviceEntry Table"
            INDEX         { deviceIndex }
            ::=  {  deviceTable 1 }

         DeviceEntry ::= SEQUENCE {
               deviceIndex
                  INTEGER,
               deviceDescription
                  DisplayString,
               deviceType
                  INTEGER,
               deviceInfo
                  DisplayString,
               deviceStatus
                  INTEGER
         }

            deviceIndex OBJECT-TYPE
               SYNTAX  INTEGER (1..184549375)
               ACCESS  read-only
               STATUS  mandatory
               DESCRIPTION
               "The index into the device table"
               ::=  {  deviceEntry 1   }

            deviceDescription OBJECT-TYPE
               SYNTAX  DisplayString
               ACCESS  read-write
               STATUS  mandatory
               DESCRIPTION
               "A Description of this device"
               ::=  {  deviceEntry 2   }

            deviceType OBJECT-TYPE
               SYNTAX  INTEGER
               ACCESS  read-only
               STATUS  mandatory
               DESCRIPTION
               "..."
               ::=  {  deviceEntry 3   }

            deviceInfo OBJECT-TYPE
               SYNTAX  DisplayString
               ACCESS  read-only
               STATUS  mandatory
               DESCRIPTION
               "A information of this device"
               ::=  {  deviceEntry 4   }

            deviceStatus OBJECT-TYPE
               SYNTAX  INTEGER
               ACCESS  read-only
               STATUS  mandatory
               DESCRIPTION
               "..."
               ::=  {  deviceEntry 5   }

         deviceIntelligentTable OBJECT-TYPE
            SYNTAX  SEQUENCE OF DeviceIntelligentEntry
            ACCESS  not-accessible
            STATUS  mandatory
            DESCRIPTION
            "This table contains the property for every plugged-in device."
            ::=  {  iMeterDevice 2  }

         deviceIntelligentEntry OBJECT-TYPE
            SYNTAX  DeviceIntelligentEntry
            ACCESS  not-accessible
            STATUS  mandatory
            DESCRIPTION
            "This is an entry in the deviceEntry Table"
            INDEX         { deviceIntelligentIndex }
            ::=  {  deviceIntelligentTable 1 }

         DeviceIntelligentEntry ::= SEQUENCE {
               deviceIntelligentIndex
                  INTEGER,
               deviceIntelligentDescription
                  DisplayString,
               deviceIntelligentInfo
                  DisplayString,
               deviceIntelligentStatus
                  INTEGER,
               sensorIntelligentTypeSelected
                  INTEGER,
               sensorIntelligentPort1GoOnline
                  INTEGER,
               sensorIntelligentPort2GoOnline
                  INTEGER,
               sensorIntelligentPort3GoOnline
                  INTEGER,
               sensorIntelligentPort4GoOnline
                  INTEGER,
               sensorIntelligentPort5GoOnline
                  INTEGER,
               sensorIntelligentPort6GoOnline
                  INTEGER,
               sensorIntelligentPort7GoOnline
                  INTEGER,
               sensorIntelligentPort8GoOnline
                  INTEGER
         }
            deviceIntelligentIndex OBJECT-TYPE
               SYNTAX  INTEGER (1..65535)
               ACCESS  read-only
               STATUS  mandatory
               DESCRIPTION
               "The index into the deviceIntelligent table"
               ::=  {  deviceIntelligentEntry 1   }

            deviceIntelligentDescription OBJECT-TYPE
               SYNTAX  DisplayString
               ACCESS  read-write
               STATUS  mandatory
               DESCRIPTION
               "A Description of this device"
               ::=  {  deviceIntelligentEntry 2   }

            deviceIntelligentInfo OBJECT-TYPE
               SYNTAX  DisplayString
               ACCESS  read-only
               STATUS  mandatory
               DESCRIPTION
               "A information of this device"
               ::=  {  deviceIntelligentEntry 4   }

            deviceIntelligentStatus OBJECT-TYPE
               SYNTAX  INTEGER
               ACCESS  read-only
               STATUS  mandatory
               DESCRIPTION
               "..."
               ::=  {  deviceIntelligentEntry 5   }

            sensorIntelligentTypeSelected OBJECT-TYPE
               SYNTAX  INTEGER
               ACCESS  read-write
               STATUS  mandatory
               DESCRIPTION
               "..."
               ::=  {  deviceIntelligentEntry 6   }

            sensorIntelligentPort1GoOnline OBJECT-TYPE
               SYNTAX  INTEGER {
               goOnline(1),
               goOffline(2)
               }
               ACCESS  read-write
               STATUS  mandatory
               DESCRIPTION
               "..."
               ::=  {  deviceIntelligentEntry 100   }

            sensorIntelligentPort2GoOnline OBJECT-TYPE
               SYNTAX  INTEGER {
               goOnline(1),
               goOffline(2)
               }
               ACCESS  read-write
               STATUS  mandatory
               DESCRIPTION
               "..."
               ::=  {  deviceIntelligentEntry 101   }

            sensorIntelligentPort3GoOnline OBJECT-TYPE
               SYNTAX  INTEGER {
               goOnline(1),
               goOffline(2)
               }
               ACCESS  read-write
               STATUS  mandatory
               DESCRIPTION
               "..."
               ::=  {  deviceIntelligentEntry 102   }

            sensorIntelligentPort4GoOnline OBJECT-TYPE
               SYNTAX  INTEGER {
               goOnline(1),
               goOffline(2)
               }
               ACCESS  read-write
               STATUS  mandatory
               DESCRIPTION
               "..."
               ::=  {  deviceIntelligentEntry 103   }

            sensorIntelligentPort5GoOnline OBJECT-TYPE
               SYNTAX  INTEGER {
               goOnline(1),
               goOffline(2)
               }
               ACCESS  read-write
               STATUS  mandatory
               DESCRIPTION
               "..."
               ::=  {  deviceIntelligentEntry 104   }

            sensorIntelligentPort6GoOnline OBJECT-TYPE
               SYNTAX  INTEGER {
               goOnline(1),
               goOffline(2)
               }
               ACCESS  read-write
               STATUS  mandatory
               DESCRIPTION
               "..."
               ::=  {  deviceIntelligentEntry 105   }

            sensorIntelligentPort7GoOnline OBJECT-TYPE
               SYNTAX  INTEGER {
               goOnline(1),
               goOffline(2)
               }
               ACCESS  read-write
               STATUS  mandatory
               DESCRIPTION
               "..."
               ::=  {  deviceIntelligentEntry 106   }

            sensorIntelligentPort8GoOnline OBJECT-TYPE
               SYNTAX  INTEGER {
               goOnline(1),
               goOffline(2)
               }
               ACCESS  read-write
               STATUS  mandatory
               DESCRIPTION
               "..."
               ::=  {  deviceIntelligentEntry 107   }

         deviceDryContactTable OBJECT-TYPE
            SYNTAX  SEQUENCE OF DeviceDryContactEntry
            ACCESS  not-accessible
            STATUS  mandatory
            DESCRIPTION
            "This table contains the property for every plugged-in device."
            ::=  {  iMeterDevice 3  }

         deviceDryContactEntry OBJECT-TYPE
            SYNTAX  DeviceDryContactEntry
            ACCESS  not-accessible
            STATUS  mandatory
            DESCRIPTION
            "This is an entry in the deviceEntry Table"
            INDEX         { deviceDryContactIndex }
            ::=  {  deviceDryContactTable 1 }

         DeviceDryContactEntry ::= SEQUENCE {
               deviceDryContactIndex
                  INTEGER,
               deviceDryContactDescription
                  DisplayString,
               deviceDryContactInfo
                  DisplayString,
               deviceDryContactStatus
                  INTEGER,
               sensorDryContactPort1GoOnline
                  INTEGER,
               sensorDryContactPort2GoOnline
                  INTEGER,
               sensorDryContactPort3GoOnline
                  INTEGER,
               sensorDryContactPort4GoOnline
                  INTEGER,
               sensorDryContactPort5GoOnline
                  INTEGER,
               sensorDryContactPort6GoOnline
                  INTEGER,
               sensorDryContactPort7GoOnline
                  INTEGER,
               sensorDryContactPort8GoOnline
                  INTEGER,
               sensorDryContactPort9GoOnline
                  INTEGER,
               sensorDryContactPort10GoOnline
                  INTEGER,
               sensorDryContactPort11GoOnline
                  INTEGER,
               sensorDryContactPort12GoOnline
                  INTEGER,
               sensorDryContactPort13GoOnline
                  INTEGER,
               sensorDryContactPort14GoOnline
                  INTEGER,
               sensorDryContactPort15GoOnline
                  INTEGER,
               sensorDryContactPort16GoOnline
                  INTEGER
         }

            deviceDryContactIndex OBJECT-TYPE
               SYNTAX  INTEGER (1..65535)
               ACCESS  read-only
               STATUS  mandatory
               DESCRIPTION
               "The index into the deviceDryContact table"
               ::=  {  deviceDryContactEntry 1   }

            deviceDryContactDescription OBJECT-TYPE
               SYNTAX  DisplayString
               ACCESS  read-write
               STATUS  mandatory
               DESCRIPTION
               "A Description of this device"
               ::=  {  deviceDryContactEntry 2   }

            deviceDryContactInfo OBJECT-TYPE
               SYNTAX  DisplayString
               ACCESS  read-only
               STATUS  mandatory
               DESCRIPTION
               "A information of this device"
               ::=  {  deviceDryContactEntry 4   }

            deviceDryContactStatus OBJECT-TYPE
               SYNTAX  INTEGER
               ACCESS  read-only
               STATUS  mandatory
               DESCRIPTION
               "..."
               ::=  {  deviceDryContactEntry 5   }

            sensorDryContactPort1GoOnline OBJECT-TYPE
               SYNTAX  INTEGER {
               goOnline(1),
               goOffline(2)
               }
               ACCESS  read-write
               STATUS  mandatory
               DESCRIPTION
               "..."
               ::=  {  deviceDryContactEntry 100   }

            sensorDryContactPort2GoOnline OBJECT-TYPE
               SYNTAX  INTEGER {
               goOnline(1),
               goOffline(2)
               }
               ACCESS  read-write
               STATUS  mandatory
               DESCRIPTION
               "..."
               ::=  {  deviceDryContactEntry 101   }

            sensorDryContactPort3GoOnline OBJECT-TYPE
               SYNTAX  INTEGER {
               goOnline(1),
               goOffline(2)
               }
               ACCESS  read-write
               STATUS  mandatory
               DESCRIPTION
               "..."
               ::=  {  deviceDryContactEntry 102   }

            sensorDryContactPort4GoOnline OBJECT-TYPE
               SYNTAX  INTEGER {
               goOnline(1),
               goOffline(2)
               }
               ACCESS  read-write
               STATUS  mandatory
               DESCRIPTION
               "..."
               ::=  {  deviceDryContactEntry 103   }

            sensorDryContactPort5GoOnline OBJECT-TYPE
               SYNTAX  INTEGER {
               goOnline(1),
               goOffline(2)
               }
               ACCESS  read-write
               STATUS  mandatory
               DESCRIPTION
               "..."
               ::=  {  deviceDryContactEntry 104   }

            sensorDryContactPort6GoOnline OBJECT-TYPE
               SYNTAX  INTEGER {
               goOnline(1),
               goOffline(2)
               }
               ACCESS  read-write
               STATUS  mandatory
               DESCRIPTION
               "..."
               ::=  {  deviceDryContactEntry 105   }

            sensorDryContactPort7GoOnline OBJECT-TYPE
               SYNTAX  INTEGER {
               goOnline(1),
               goOffline(2)
               }
               ACCESS  read-write
               STATUS  mandatory
               DESCRIPTION
               "..."
               ::=  {  deviceDryContactEntry 106   }

            sensorDryContactPort8GoOnline OBJECT-TYPE
               SYNTAX  INTEGER {
               goOnline(1),
               goOffline(2)
               }
               ACCESS  read-write
               STATUS  mandatory
               DESCRIPTION
               "..."
               ::=  {  deviceDryContactEntry 107   }

            sensorDryContactPort9GoOnline OBJECT-TYPE
               SYNTAX  INTEGER {
               goOnline(1),
               goOffline(2)
               }
               ACCESS  read-write
               STATUS  mandatory
               DESCRIPTION
               "..."
               ::=  {  deviceDryContactEntry 108   }

            sensorDryContactPort10GoOnline OBJECT-TYPE
               SYNTAX  INTEGER {
               goOnline(1),
               goOffline(2)
               }
               ACCESS  read-write
               STATUS  mandatory
               DESCRIPTION
               "..."
               ::=  {  deviceDryContactEntry 109   }

            sensorDryContactPort11GoOnline OBJECT-TYPE
               SYNTAX  INTEGER {
               goOnline(1),
               goOffline(2)
               }
               ACCESS  read-write
               STATUS  mandatory
               DESCRIPTION
               "..."
               ::=  {  deviceDryContactEntry 110   }

            sensorDryContactPort12GoOnline OBJECT-TYPE
               SYNTAX  INTEGER {
               goOnline(1),
               goOffline(2)
               }
               ACCESS  read-write
               STATUS  mandatory
               DESCRIPTION
               "..."
               ::=  {  deviceDryContactEntry 111   }

            sensorDryContactPort13GoOnline OBJECT-TYPE
               SYNTAX  INTEGER {
               goOnline(1),
               goOffline(2)
               }
               ACCESS  read-write
               STATUS  mandatory
               DESCRIPTION
               "..."
               ::=  {  deviceDryContactEntry 112   }

            sensorDryContactPort14GoOnline OBJECT-TYPE
               SYNTAX  INTEGER {
               goOnline(1),
               goOffline(2)
               }
               ACCESS  read-write
               STATUS  mandatory
               DESCRIPTION
               "..."
               ::=  {  deviceDryContactEntry 113   }

            sensorDryContactPort15GoOnline OBJECT-TYPE
               SYNTAX  INTEGER {
               goOnline(1),
               goOffline(2)
               }
               ACCESS  read-write
               STATUS  mandatory
               DESCRIPTION
               "..."
               ::=  {  deviceDryContactEntry 114   }

            sensorDryContactPort16GoOnline OBJECT-TYPE
               SYNTAX  INTEGER {
               goOnline(1),
               goOffline(2)
               }
               ACCESS  read-write
               STATUS  mandatory
               DESCRIPTION
               "..."
               ::=  {  deviceDryContactEntry 115   }


      iMeterSensor OBJECT IDENTIFIER  ::=  {  iMeter 3 }

         sensorTable OBJECT-TYPE
            SYNTAX  SEQUENCE OF SensorEntry
            ACCESS  not-accessible
            STATUS  mandatory
            DESCRIPTION
            "This table contains the property and reading value for every sensor."
            ::=  {  iMeterSensor 1   }

--/* Begin of sensorEntry */

         sensorEntry OBJECT-TYPE
            SYNTAX  SensorEntry
            ACCESS  not-accessible
            STATUS  mandatory
            DESCRIPTION
            "This is an entry in the sensorTable Table"
            INDEX         { sensorIndex }
            ::=  {  sensorTable 1 }

         SensorEntry ::= SEQUENCE {
               sensorIndex
                  INTEGER,
               sensorDescription
                  DisplayString,
               sensorType
                  INTEGER,
               sensorValue
                  INTEGER,
               sensorUnit
                  DisplayString,
               sensorStatus
                  INTEGER,
               sensorGoOffline
                  INTEGER,
               sensorPort
                  INTEGER,
               sensorSubPort
                  INTEGER,
               sensorDeviceIndex
                  INTEGER
         }

            sensorIndex OBJECT-TYPE
               SYNTAX  INTEGER (1..65535)
               ACCESS  read-only
               STATUS  mandatory
               DESCRIPTION
               "The index into the sensor table"
               ::=  {  sensorEntry 1   }

            sensorDescription OBJECT-TYPE
               SYNTAX  DisplayString
               ACCESS  read-write
               STATUS  mandatory
               DESCRIPTION
               "A Description of this sensor"
               ::=  {  sensorEntry 2   }

            sensorType OBJECT-TYPE
               SYNTAX  INTEGER {
                    temperature(1),
                    dual-humidity(2),
                    dual-temperature(3),
                    intelliVolt(4),
                    intelliAmp(5),
                    airflow(6),
                    io(7),
                    drycontact(8),
                    motion(9),
                    water(10),
                    security(11),
                    siren(12),
                    relay(13),
                    acvoltage(14),
                    thermocouple(20),
                    smoke(21),
                    virtual(129)
               }
               ACCESS  read-only
               STATUS  mandatory
               DESCRIPTION
               "Enter the type of this Sensor"
               ::=  {  sensorEntry 3  }

            sensorValue OBJECT-TYPE
               SYNTAX  INTEGER
               ACCESS  read-only
               STATUS  mandatory
               DESCRIPTION
               "The value in this sensor"
               ::=  {  sensorEntry 4   }

            sensorUnit OBJECT-TYPE
               SYNTAX  DisplayString
               ACCESS  read-only
               STATUS  mandatory
               DESCRIPTION
               "The unit string"
               ::=  {  sensorEntry 5  }

            sensorStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this sensor"
               ::=  {  sensorEntry 6   }

            sensorGoOffline OBJECT-TYPE
               SYNTAX  INTEGER {
                  online(1),
                  goOffline(2)
               }
               ACCESS  read-write
               STATUS  mandatory
               DESCRIPTION
               "To take offline enter a 2"
               ::=  {  sensorEntry 8   }

            sensorPort OBJECT-TYPE
               SYNTAX  INTEGER (0..65534)
               ACCESS  read-only
               STATUS  mandatory
               DESCRIPTION
               "Sensor port"
               ::=  {  sensorEntry 35 }

            sensorSubPort OBJECT-TYPE
               SYNTAX  INTEGER (0..65534)
               ACCESS  read-only
               STATUS  mandatory
               DESCRIPTION
               "Sensor sub port"
               ::=  {  sensorEntry 36 }

            sensorDeviceIndex OBJECT-TYPE
               SYNTAX  INTEGER (0..65534)
               ACCESS  read-only
               STATUS  mandatory
               DESCRIPTION
               "Device Index of sensor"
               ::=  {  sensorEntry 37 }

--/* End of sensorEntry */

--/* Begin of sensorTemperatureEntry */
         sensorTemperatureTable OBJECT-TYPE
            SYNTAX  SEQUENCE OF SensorTemperatureEntry
            ACCESS  not-accessible
            STATUS  mandatory
            DESCRIPTION
            "This table contains the property and reading value for every Temperature sensor."
            ::=  {  iMeterSensor 2   }

         sensorTemperatureEntry OBJECT-TYPE
            SYNTAX  SensorTemperatureEntry
            ACCESS  not-accessible
            STATUS  mandatory
            DESCRIPTION
            "This is an entry in the sensorTemperatureEntry Table"
            INDEX         { sensorTemperatureIndex }
            ::=  {  sensorTemperatureTable 1 }

         SensorTemperatureEntry ::= SEQUENCE {
               sensorTemperatureIndex
                  INTEGER,
               sensorTemperatureDescription
                  DisplayString,
               sensorTemperatureType
                  INTEGER,
               sensorTemperatureDegree
                  INTEGER,
               sensorTemperatureUnit
                  DisplayString,
               sensorTemperatureStatus
                  INTEGER,               
               sensorTemperatureGoOffline
                  INTEGER,
               sensorTemperatureLowCritical
                  INTEGER,
               sensorTemperatureLowWarning
                  INTEGER,
               sensorTemperatureHighWarning
                  INTEGER,
               sensorTemperatureHighCritical
                  INTEGER,
               sensorTemperatureRearm
                  INTEGER,
               sensorTemperatureDelayError
                  INTEGER,
               sensorTemperatureDelayNormal
                  INTEGER,
               sensorTemperatureDelayLowCritical
                  INTEGER,
               sensorTemperatureDelayLowWarning
                  INTEGER,
               sensorTemperatureDelayHighWarning
                  INTEGER,
               sensorTemperatureDelayHighCritical
                  INTEGER,
               sensorTemperatureRaw
                  INTEGER,
               sensorTemperatureOffset
                  INTEGER,
               sensorTemperaturePort
                  INTEGER,
               sensorTemperatureSubPort
                  INTEGER,
               sensorTemperatureDeviceIndex
                  INTEGER
            }

            sensorTemperatureIndex OBJECT-TYPE
               SYNTAX  INTEGER (1..65535)
               ACCESS  read-only
               STATUS  mandatory
               DESCRIPTION
               "The index into the sensor table"
               ::=  {  sensorTemperatureEntry 1   }

            sensorTemperatureDescription OBJECT-TYPE
               SYNTAX  DisplayString
               ACCESS  read-write
               STATUS  mandatory
               DESCRIPTION
               "A Description of this sensor"
               ::=  {  sensorTemperatureEntry 2   }

            sensorTemperatureType OBJECT-TYPE
               SYNTAX  INTEGER {
                  temperature(1),
                  dualsensor(3),
                  thermocouple(20)
               }
               ACCESS  read-only
               STATUS  mandatory
               DESCRIPTION
               "Enter the type of this Sensor"
               ::=  {  sensorTemperatureEntry 3  }

            sensorTemperatureDegree OBJECT-TYPE
               SYNTAX  INTEGER
               ACCESS  read-only
               STATUS  mandatory
               DESCRIPTION
               "The degrees in this sensor"
               ::=  {  sensorTemperatureEntry 4   }

            sensorTemperatureUnit OBJECT-TYPE
               SYNTAX  DisplayString
               ACCESS  read-only
               STATUS  mandatory
               DESCRIPTION
               "The unit string"
               ::=  {  sensorTemperatureEntry 5  }

            sensorTemperatureStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorTemperatureEntry 6   }
   
            sensorTemperatureGoOffline OBJECT-TYPE
               SYNTAX  INTEGER {
                  online(1),
                  goOffline(2)
               }
               ACCESS  read-write
               STATUS  mandatory
               DESCRIPTION
               "To take offline enter a 2"
               ::=  {  sensorTemperatureEntry 8   }

            sensorTemperatureLowCritical OBJECT-TYPE
               SYNTAX  INTEGER
               ACCESS  read-write
               STATUS  mandatory
               DESCRIPTION
               "How cold this sensor gets before it sends a critical event"
               ::=  {  sensorTemperatureEntry 9   }

            sensorTemperatureLowWarning OBJECT-TYPE
               SYNTAX  INTEGER
               ACCESS  read-write
               STATUS  mandatory
               DESCRIPTION
               "How cold this sensor gets before it sends a warning"
               ::=  {  sensorTemperatureEntry 10   }
   
            sensorTemperatureHighWarning OBJECT-TYPE
               SYNTAX  INTEGER
               ACCESS  read-write
               STATUS  mandatory
               DESCRIPTION
               "How hot this sensor gets before it sends a warning"
               ::=  {  sensorTemperatureEntry 11   }  

            sensorTemperatureHighCritical OBJECT-TYPE
               SYNTAX  INTEGER
               ACCESS  read-write
               STATUS  mandatory
               DESCRIPTION
               "How hot this sensor gets before it sends a critical event"
               ::=  {  sensorTemperatureEntry 12   }   

            sensorTemperatureRearm OBJECT-TYPE
               SYNTAX  INTEGER
               ACCESS  read-write
               STATUS  mandatory
               DESCRIPTION
               "The number of degrees to rearm the status. For example if status goes from normal to warning, the temp must go down iMTempRearm degrees below warning before the status goes to normal"
               ::=  {  sensorTemperatureEntry 13   }

            sensorTemperatureDelayError OBJECT-TYPE
               SYNTAX  INTEGER (0..65534)
               ACCESS  read-write
               STATUS  mandatory
               DESCRIPTION
               "Time in seconds after the sensor has been in error status before report as an error"
               ::=  {  sensorTemperatureEntry 14   }

            sensorTemperatureDelayNormal OBJECT-TYPE
               SYNTAX  INTEGER (0..65534)
               ACCESS  read-write
               STATUS  mandatory
               DESCRIPTION
               "Time in seconds after the sensor change from error to normal before report as normal"
               ::=  {  sensorTemperatureEntry 15   }

            sensorTemperatureDelayLowCritical OBJECT-TYPE
               SYNTAX INTEGER (0..65535)
               ACCESS read-write
               STATUS mandatory
               DESCRIPTION
               "Continuous time for this sensor to be in Low Critical before accepting new Status."
               ::= {  sensorTemperatureEntry 16 }
               
            sensorTemperatureDelayLowWarning OBJECT-TYPE
               SYNTAX INTEGER (0..65535)
               ACCESS read-write
               STATUS mandatory
               DESCRIPTION
               "Continuous time for this sensor to be in Low Warning before accepting new Status."
               ::= {  sensorTemperatureEntry 17 }

            sensorTemperatureDelayHighWarning OBJECT-TYPE
               SYNTAX INTEGER (0..65535)
               ACCESS read-write
               STATUS mandatory
               DESCRIPTION
               "Continuous time for this sensor to be in High Warning before accepting new Status."
               ::= {  sensorTemperatureEntry 18 }

            sensorTemperatureDelayHighCritical OBJECT-TYPE
               SYNTAX INTEGER (0..65535)
               ACCESS read-write
               STATUS mandatory
               DESCRIPTION
               "Continuous time for this sensor to be in High Critical before accepting new Status."
               ::= {  sensorTemperatureEntry 19 }

            sensorTemperatureRaw OBJECT-TYPE
               SYNTAX  INTEGER 
               ACCESS  read-only
               STATUS  mandatory
               DESCRIPTION
               "The raw degree data from the temperature sensor, slightly higher resolution"
               ::=  {  sensorTemperatureEntry 20 }

            sensorTemperatureOffset OBJECT-TYPE
               SYNTAX  INTEGER
               ACCESS  read-write
               STATUS  mandatory
               DESCRIPTION
               "Temperature Offset reading"
               ::=  {  sensorTemperatureEntry 21 }

            sensorTemperaturePort OBJECT-TYPE
               SYNTAX  INTEGER (0..65534)
               ACCESS  read-only
               STATUS  mandatory
               DESCRIPTION
               "Sensor port"
               ::=  {  sensorTemperatureEntry 35 }

            sensorTemperatureSubPort OBJECT-TYPE
               SYNTAX  INTEGER (0..65534)
               ACCESS  read-only
               STATUS  mandatory
               DESCRIPTION
               "Sensor sub port"
               ::=  {  sensorTemperatureEntry 36 }

            sensorTemperatureDeviceIndex OBJECT-TYPE
               SYNTAX  INTEGER (0..65534)
               ACCESS  read-only
               STATUS  mandatory
               DESCRIPTION
               "Device Index of sensor"
               ::=  {  sensorTemperatureEntry 37 }

--/* End of sensorTemperatureEntry */

--/* Begin of sensorHumidityEntry */
         sensorHumidityTable OBJECT-TYPE
            SYNTAX  SEQUENCE OF SensorHumidityEntry
            ACCESS  not-accessible
            STATUS  mandatory
            DESCRIPTION
            "This table contains the property and reading value for every sensor."
            ::=  {  iMeterSensor 3   }

         sensorHumidityEntry OBJECT-TYPE
            SYNTAX  SensorHumidityEntry
            ACCESS  not-accessible
            STATUS  mandatory
            DESCRIPTION
            "This is an entry in the sensorTemperatureEntry Table"
            INDEX         { sensorHumidityIndex }
            ::=  {  sensorHumidityTable 1 }

         SensorHumidityEntry ::= SEQUENCE {
               sensorHumidityIndex
                  INTEGER,
               sensorHumidityDescription
                  DisplayString,
               sensorHumidityPercent
                  INTEGER,
               sensorHumidityUnit
                  DisplayString,
               sensorHumidityStatus
                  INTEGER,
               sensorHumidityGoOffline
                  INTEGER,
               sensorHumidityLowCritical
                  INTEGER,
               sensorHumidityLowWarning
                  INTEGER,
               sensorHumidityHighWarning
                  INTEGER,
               sensorHumidityHighCritical
                  INTEGER,
               sensorHumidityRearm
                  INTEGER,
               sensorHumidityDelayError
                  INTEGER,
               sensorHumidityDelayNormal
                  INTEGER,
               sensorHumidityDelayLowCritical
                  INTEGER,
               sensorHumidityDelayLowWarning
                  INTEGER,
               sensorHumidityDelayHighWarning
                  INTEGER,
               sensorHumidityDelayHighCritical
                  INTEGER,
               sensorHumidityRaw
                  INTEGER,
               sensorHumidityOffset
                  INTEGER,
               sensorHumidityPort
                  INTEGER,
               sensorHumiditySubPort
                  INTEGER,
               sensorHumidityDeviceIndex
                  INTEGER
            }

            sensorHumidityIndex OBJECT-TYPE
               SYNTAX  INTEGER (1..65535)
               ACCESS  read-only
               STATUS  mandatory
               DESCRIPTION
               "The index into the sensor table"
               ::=  {  sensorHumidityEntry 1   }

            sensorHumidityDescription OBJECT-TYPE
               SYNTAX  DisplayString
               ACCESS  read-write
               STATUS  mandatory
               DESCRIPTION
               "A Description of this sensor"
               ::=  {  sensorHumidityEntry 2   }

            sensorHumidityPercent OBJECT-TYPE
               SYNTAX  INTEGER
               ACCESS  read-only
               STATUS  mandatory
               DESCRIPTION
               "The relative humidity percentage measured by this sensor"
               ::=  {  sensorHumidityEntry 4   }

            sensorHumidityUnit OBJECT-TYPE
               SYNTAX  DisplayString
               ACCESS  read-write
               STATUS  mandatory
               DESCRIPTION
               "The unit string"
               ::=  {  sensorHumidityEntry 5  }

            sensorHumidityStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorHumidityEntry 6   }

            sensorHumidityGoOffline OBJECT-TYPE
               SYNTAX  INTEGER {
                  online(1),
                  goOffline(2)
               }
               ACCESS  read-write
               STATUS  mandatory
               DESCRIPTION
               "To take offline enter a 2"
               ::=  {  sensorHumidityEntry 8   }

            sensorHumidityLowCritical OBJECT-TYPE
               SYNTAX  INTEGER
               ACCESS  read-write
               STATUS  mandatory
               DESCRIPTION
               "How cold this sensor gets before it sends a critical event"
               ::=  {  sensorHumidityEntry 9   }

            sensorHumidityLowWarning OBJECT-TYPE
               SYNTAX  INTEGER
               ACCESS  read-write
               STATUS  mandatory
               DESCRIPTION
               "How cold this sensor gets before it sends a warning"
               ::=  {  sensorHumidityEntry 10   }
   
            sensorHumidityHighWarning OBJECT-TYPE
               SYNTAX  INTEGER
               ACCESS  read-write
               STATUS  mandatory
               DESCRIPTION
               "How hot this sensor gets before it sends a warning"
               ::=  {  sensorHumidityEntry 11   }  

            sensorHumidityHighCritical OBJECT-TYPE
               SYNTAX  INTEGER
               ACCESS  read-write
               STATUS  mandatory
               DESCRIPTION
               "How hot this sensor gets before it sends a critical event"
               ::=  {  sensorHumidityEntry 12   }   

            sensorHumidityRearm OBJECT-TYPE
               SYNTAX  INTEGER
               ACCESS  read-write
               STATUS  mandatory
               DESCRIPTION
               "The number of degrees to rearm the status. For example if status goes from normal to warning, the temp must go down iMTempRearm degrees below warning before the status goes to normal"
               ::=  {  sensorHumidityEntry 13   }

            sensorHumidityDelayError OBJECT-TYPE
               SYNTAX  INTEGER (0..65534)
               ACCESS  read-write
               STATUS  mandatory
               DESCRIPTION
               "Time in seconds after the sensor has been in error status before report as an error"
               ::=  {  sensorHumidityEntry 14   }

            sensorHumidityDelayNormal OBJECT-TYPE
               SYNTAX  INTEGER (0..65534)
               ACCESS  read-write
               STATUS  mandatory
               DESCRIPTION
               "Time in seconds after the sensor change from error to normal before report as normal"
               ::=  {  sensorHumidityEntry 15   }

            sensorHumidityDelayLowCritical OBJECT-TYPE
               SYNTAX INTEGER (0..65535)
               ACCESS read-write
               STATUS mandatory
               DESCRIPTION
               "Continuous time for this sensor to be in Low Critical before accepting new Status."
               ::= {  sensorHumidityEntry 16 }
               
            sensorHumidityDelayLowWarning OBJECT-TYPE
               SYNTAX INTEGER (0..65535)
               ACCESS read-write
               STATUS mandatory
               DESCRIPTION
               "Continuous time for this sensor to be in Low Warning before accepting new Status."
               ::= {  sensorHumidityEntry 17 }

            sensorHumidityDelayHighWarning OBJECT-TYPE
               SYNTAX INTEGER (0..65535)
               ACCESS read-write
               STATUS mandatory
               DESCRIPTION
               "Continuous time for this sensor to be in High Warning before accepting new Status."
               ::= {  sensorHumidityEntry 18 }

            sensorHumidityDelayHighCritical OBJECT-TYPE
               SYNTAX INTEGER (0..65535)
               ACCESS read-write
               STATUS mandatory
               DESCRIPTION
               "Continuous time for this sensor to be in High Critical before accepting new Status."
               ::= {  sensorHumidityEntry 19 }

            sensorHumidityRaw OBJECT-TYPE
               SYNTAX  INTEGER 
               ACCESS  read-only
               STATUS  mandatory
               DESCRIPTION
               "The unformatted, raw, A/D value in this sensor. Contains more resolution than the formated percentage. This number can go from 0 to 1023 depending on the input voltage"
               ::=  {  sensorHumidityEntry 20   }

            sensorHumidityOffset OBJECT-TYPE
               SYNTAX  INTEGER
               ACCESS  read-write
               STATUS  mandatory
               DESCRIPTION
               "Humidity Offset reading"
               ::=  {  sensorHumidityEntry 21   }

            sensorHumidityPort OBJECT-TYPE
               SYNTAX  INTEGER (0..65534)
               ACCESS  read-only
               STATUS  mandatory
               DESCRIPTION
               "Sensor port"
               ::=  {  sensorHumidityEntry 35 }

            sensorHumiditySubPort OBJECT-TYPE
               SYNTAX  INTEGER (0..65534)
               ACCESS  read-only
               STATUS  mandatory
               DESCRIPTION
               "Sensor sub port"
               ::=  {  sensorHumidityEntry 36 }

            sensorHumidityDeviceIndex OBJECT-TYPE
               SYNTAX  INTEGER (0..65534)
               ACCESS  read-only
               STATUS  mandatory
               DESCRIPTION
               "Device Index of sensor"
               ::=  {  sensorHumidityEntry 37 }

--/* End of sensorHumidityEntry */

--/* Begin of sensorIntelliVoltEntry */
         sensorIntelliVoltTable OBJECT-TYPE
            SYNTAX  SEQUENCE OF SensorIntelliVoltEntry
            ACCESS  not-accessible
            STATUS  mandatory
            DESCRIPTION
            "This table contains the property and reading value for every sensor."
            ::=  {  iMeterSensor 5   }

         sensorIntelliVoltEntry OBJECT-TYPE
            SYNTAX  SensorIntelliVoltEntry
            ACCESS  not-accessible
            STATUS  mandatory
            DESCRIPTION
            "This is an entry in the sensorTemperatureEntry Table"
            INDEX         { sensorIntelliVoltIndex }
            ::=  {  sensorIntelliVoltTable 1 }

         SensorIntelliVoltEntry ::= SEQUENCE {
               sensorIntelliVoltIndex
                  INTEGER,
               sensorIntelliVoltDescription
                  DisplayString,
               sensorIntelliVoltValue
                  INTEGER,
               sensorIntelliVoltUnit
                  DisplayString,
               sensorIntelliVoltStatus
                  INTEGER,
               sensorIntelliVoltGoOffline
                  INTEGER,
               sensorIntelliVoltLowCritical
                  INTEGER,
               sensorIntelliVoltLowWarning
                  INTEGER,
               sensorIntelliVoltHighWarning
                  INTEGER,
               sensorIntelliVoltHighCritical
                  INTEGER,
               sensorIntelliVoltRearm
                  INTEGER,
               sensorIntelliVoltDelayError
                  INTEGER,
               sensorIntelliVoltDelayNormal
                  INTEGER,
               sensorIntelliVoltDelayLowCritical
                  INTEGER,
               sensorIntelliVoltDelayLowWarning
                  INTEGER,
               sensorIntelliVoltDelayHighWarning
                  INTEGER,
               sensorIntelliVoltDelayHighCritical
                  INTEGER,
               sensorIntelliVoltRaw
                  INTEGER,
               sensorIntelliVoltOffset
                  INTEGER,
               sensorIntelliVoltAmountMaxVoltage
                  INTEGER,
               sensorIntelliVoltAmountBaseVoltage
                  INTEGER,
               sensorIntelliVoltPort
                  INTEGER,
               sensorIntelliVoltSubPort
                  INTEGER,
               sensorIntelliVoltDeviceIndex
                  INTEGER,
               sensorIntelliVoltMaxVoltage
                  INTEGER,
               sensorIntelliVoltBaseVoltage
                  INTEGER
            }

            sensorIntelliVoltIndex OBJECT-TYPE
               SYNTAX  INTEGER (1..65535)
               ACCESS  read-only
               STATUS  mandatory
               DESCRIPTION
               "The index into the sensor table"
               ::=  {  sensorIntelliVoltEntry 1   }

            sensorIntelliVoltDescription OBJECT-TYPE
               SYNTAX  DisplayString
               ACCESS  read-write
               STATUS  mandatory
               DESCRIPTION
               "A Description of this sensor"
               ::=  {  sensorIntelliVoltEntry 2   }

            sensorIntelliVoltValue OBJECT-TYPE
               SYNTAX  INTEGER
               ACCESS  read-only
               STATUS  mandatory
               DESCRIPTION
               "The reading value in this sensor"
               ::=  {  sensorIntelliVoltEntry 4   }

            sensorIntelliVoltUnit OBJECT-TYPE
               SYNTAX  DisplayString
               ACCESS  read-write
               STATUS  mandatory
               DESCRIPTION
               "The unit string"
               ::=  {  sensorIntelliVoltEntry 5  }

            sensorIntelliVoltStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorIntelliVoltEntry 6   }

            sensorIntelliVoltGoOffline OBJECT-TYPE
               SYNTAX  INTEGER {
                  online(1),
                  goOffline(2)
               }
               ACCESS  read-write
               STATUS  mandatory
               DESCRIPTION
               "To take offline enter a 2"
               ::=  {  sensorIntelliVoltEntry 8   }

            sensorIntelliVoltLowCritical OBJECT-TYPE
               SYNTAX  INTEGER
               ACCESS  read-write
               STATUS  mandatory
               DESCRIPTION
               "How cold this sensor gets before it sends a critical event"
               ::=  {  sensorIntelliVoltEntry 9   }

            sensorIntelliVoltLowWarning OBJECT-TYPE
               SYNTAX  INTEGER
               ACCESS  read-write
               STATUS  mandatory
               DESCRIPTION
               "How cold this sensor gets before it sends a warning"
               ::=  {  sensorIntelliVoltEntry 10   }
   
            sensorIntelliVoltHighWarning OBJECT-TYPE
               SYNTAX  INTEGER
               ACCESS  read-write
               STATUS  mandatory
               DESCRIPTION
               "How hot this sensor gets before it sends a warning"
               ::=  {  sensorIntelliVoltEntry 11   }  

            sensorIntelliVoltHighCritical OBJECT-TYPE
               SYNTAX  INTEGER
               ACCESS  read-write
               STATUS  mandatory
               DESCRIPTION
               "How hot this sensor gets before it sends a critical event"
               ::=  {  sensorIntelliVoltEntry 12   }   

            sensorIntelliVoltRearm OBJECT-TYPE
               SYNTAX  INTEGER
               ACCESS  read-write
               STATUS  mandatory
               DESCRIPTION
               "The number of degrees to rearm the status. For example if status goes from normal to warning, the temp must go down iMTempRearm degrees below warning before the status goes to normal"
               ::=  {  sensorIntelliVoltEntry 13   }

            sensorIntelliVoltDelayError OBJECT-TYPE
               SYNTAX  INTEGER (0..65534)
               ACCESS  read-write
               STATUS  mandatory
               DESCRIPTION
               "Time in seconds after the sensor has been in error status before report as an error"
               ::=  {  sensorIntelliVoltEntry 14   }

            sensorIntelliVoltDelayNormal OBJECT-TYPE
               SYNTAX  INTEGER (0..65534)
               ACCESS  read-write
               STATUS  mandatory
               DESCRIPTION
               "Time in seconds after the sensor change from error to normal before report as normal"
               ::=  {  sensorIntelliVoltEntry 15   }

            sensorIntelliVoltDelayLowCritical OBJECT-TYPE
               SYNTAX INTEGER (0..65535)
               ACCESS read-write
               STATUS mandatory
               DESCRIPTION
               "Continuous time for this sensor to be in Low Critical before accepting new Status."
               ::= {  sensorIntelliVoltEntry 16 }
               
            sensorIntelliVoltDelayLowWarning OBJECT-TYPE
               SYNTAX INTEGER (0..65535)
               ACCESS read-write
               STATUS mandatory
               DESCRIPTION
               "Continuous time for this sensor to be in Low Warning before accepting new Status."
               ::= {  sensorIntelliVoltEntry 17 }

            sensorIntelliVoltDelayHighWarning OBJECT-TYPE
               SYNTAX INTEGER (0..65535)
               ACCESS read-write
               STATUS mandatory
               DESCRIPTION
               "Continuous time for this sensor to be in High Warning before accepting new Status."
               ::= {  sensorIntelliVoltEntry 18 }

            sensorIntelliVoltDelayHighCritical OBJECT-TYPE
               SYNTAX INTEGER (0..65535)
               ACCESS read-write
               STATUS mandatory
               DESCRIPTION
               "Continuous time for this sensor to be in High Critical before accepting new Status."
               ::= {  sensorIntelliVoltEntry 19 }

            sensorIntelliVoltRaw OBJECT-TYPE
               SYNTAX  INTEGER 
               ACCESS  read-only
               STATUS  mandatory
               DESCRIPTION
               "The unformatted, raw, A/D value in this sensor. Contains more resolution than the formated percentage. This number can go from 0 to 1023 depending on the input voltage"
               ::=  {  sensorIntelliVoltEntry 20   }

            sensorIntelliVoltOffset OBJECT-TYPE
               SYNTAX  INTEGER
               ACCESS  read-write
               STATUS  mandatory
               DESCRIPTION
               "IntelliVolt Offset reading"
               ::=  {  sensorIntelliVoltEntry 21   }

            sensorIntelliVoltAmountMaxVoltage OBJECT-TYPE
               SYNTAX  INTEGER
               ACCESS  read-write
               STATUS  mandatory
               DESCRIPTION
               "The maximum scale of IntelliVolt conversion."
               ::=  {  sensorIntelliVoltEntry 33   }

            sensorIntelliVoltAmountBaseVoltage OBJECT-TYPE
               SYNTAX  INTEGER
               ACCESS  read-write
               STATUS  mandatory
               DESCRIPTION
               "The base scale of IntelliVolt conversion."
               ::=  {  sensorIntelliVoltEntry 34   }

            sensorIntelliVoltPort OBJECT-TYPE
               SYNTAX  INTEGER (0..65534)
               ACCESS  read-only
               STATUS  mandatory
               DESCRIPTION
               "Sensor port"
               ::=  {  sensorIntelliVoltEntry 35 }

            sensorIntelliVoltSubPort OBJECT-TYPE
               SYNTAX  INTEGER (0..65534)
               ACCESS  read-only
               STATUS  mandatory
               DESCRIPTION
               "Sensor sub port"
               ::=  {  sensorIntelliVoltEntry 36 }

            sensorIntelliVoltDeviceIndex OBJECT-TYPE
               SYNTAX  INTEGER (0..65534)
               ACCESS  read-only
               STATUS  mandatory
               DESCRIPTION
               "Device Index of sensor"
               ::=  {  sensorIntelliVoltEntry 37 }

            sensorIntelliVoltMaxVoltage OBJECT-TYPE
               SYNTAX  INTEGER
               ACCESS  read-write
               STATUS  mandatory
               DESCRIPTION
               "The max range for use in conversion."
               ::=  {  sensorIntelliVoltEntry 43   }

            sensorIntelliVoltBaseVoltage OBJECT-TYPE
               SYNTAX  INTEGER
               ACCESS  read-write
               STATUS  mandatory
               DESCRIPTION
               "The base range for use in conversion."
               ::=  {  sensorIntelliVoltEntry 44   }

--/* End of sensorIntelliVoltEntry */

--/* Begin of sensorIntelliAmpEntry */
         sensorIntelliAmpTable OBJECT-TYPE
            SYNTAX  SEQUENCE OF SensorIntelliAmpEntry
            ACCESS  not-accessible
            STATUS  mandatory
            DESCRIPTION
            "This table contains the property and reading value for every sensor."
            ::=  {  iMeterSensor 6   }

         sensorIntelliAmpEntry OBJECT-TYPE
            SYNTAX  SensorIntelliAmpEntry
            ACCESS  not-accessible
            STATUS  mandatory
            DESCRIPTION
            "This is an entry in the sensorTemperatureEntry Table"
            INDEX         { sensorIntelliAmpIndex }
            ::=  {  sensorIntelliAmpTable 1 }

         SensorIntelliAmpEntry ::= SEQUENCE {
               sensorIntelliAmpIndex
                  INTEGER,
               sensorIntelliAmpDescription
                  DisplayString,
               sensorIntelliAmpValue
                  INTEGER,
               sensorIntelliAmpUnit
                  DisplayString,
               sensorIntelliAmpStatus
                  INTEGER,
               sensorIntelliAmpGoOffline
                  INTEGER,
               sensorIntelliAmpLowCritical
                  INTEGER,
               sensorIntelliAmpLowWarning
                  INTEGER,
               sensorIntelliAmpHighWarning
                  INTEGER,
               sensorIntelliAmpHighCritical
                  INTEGER,
               sensorIntelliAmpRearm
                  INTEGER,
               sensorIntelliAmpDelayError
                  INTEGER,
               sensorIntelliAmpDelayNormal
                  INTEGER,
               sensorIntelliAmpDelayLowCritical
                  INTEGER,
               sensorIntelliAmpDelayLowWarning
                  INTEGER,
               sensorIntelliAmpDelayHighWarning
                  INTEGER,
               sensorIntelliAmpDelayHighCritical
                  INTEGER,
               sensorIntelliAmpRaw
                  INTEGER,
               sensorIntelliAmpOffset
                  INTEGER,
               sensorIntelliAmpJumper
                  INTEGER,
               sensorIntelliAmpAmountMaxVoltage
                  INTEGER,
               sensorIntelliAmpAmountBaseVoltage
                  INTEGER,
               sensorIntelliAmpPort
                  INTEGER,
               sensorIntelliAmpSubPort
                  INTEGER,
               sensorIntelliAmpDeviceIndex
                  INTEGER,
               sensorIntelliAmpMaxVoltage
                  INTEGER,
               sensorIntelliAmpBaseVoltage
                  INTEGER
            }

            sensorIntelliAmpIndex OBJECT-TYPE
               SYNTAX  INTEGER (1..65535)
               ACCESS  read-only
               STATUS  mandatory
               DESCRIPTION
               "The index into the sensor table"
               ::=  {  sensorIntelliAmpEntry 1   }

            sensorIntelliAmpDescription OBJECT-TYPE
               SYNTAX  DisplayString
               ACCESS  read-write
               STATUS  mandatory
               DESCRIPTION
               "A Description of this sensor"
               ::=  {  sensorIntelliAmpEntry 2   }

            sensorIntelliAmpValue OBJECT-TYPE
               SYNTAX  INTEGER
               ACCESS  read-only
               STATUS  mandatory
               DESCRIPTION
               "The reading value in this sensor"
               ::=  {  sensorIntelliAmpEntry 4   }

            sensorIntelliAmpUnit OBJECT-TYPE
               SYNTAX  DisplayString
               ACCESS  read-write
               STATUS  mandatory
               DESCRIPTION
               "The unit string"
               ::=  {  sensorIntelliAmpEntry 5  }

            sensorIntelliAmpStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorIntelliAmpEntry 6   }

            sensorIntelliAmpGoOffline OBJECT-TYPE
               SYNTAX  INTEGER {
                  online(1),
                  goOffline(2)
               }
               ACCESS  read-write
               STATUS  mandatory
               DESCRIPTION
               "To take offline enter a 2"
               ::=  {  sensorIntelliAmpEntry 8   }

            sensorIntelliAmpLowCritical OBJECT-TYPE
               SYNTAX  INTEGER
               ACCESS  read-write
               STATUS  mandatory
               DESCRIPTION
               "How cold this sensor gets before it sends a critical event"
               ::=  {  sensorIntelliAmpEntry 9   }

            sensorIntelliAmpLowWarning OBJECT-TYPE
               SYNTAX  INTEGER
               ACCESS  read-write
               STATUS  mandatory
               DESCRIPTION
               "How cold this sensor gets before it sends a warning"
               ::=  {  sensorIntelliAmpEntry 10   }
   
            sensorIntelliAmpHighWarning OBJECT-TYPE
               SYNTAX  INTEGER
               ACCESS  read-write
               STATUS  mandatory
               DESCRIPTION
               "How hot this sensor gets before it sends a warning"
               ::=  {  sensorIntelliAmpEntry 11   }  

            sensorIntelliAmpHighCritical OBJECT-TYPE
               SYNTAX  INTEGER
               ACCESS  read-write
               STATUS  mandatory
               DESCRIPTION
               "How hot this sensor gets before it sends a critical event"
               ::=  {  sensorIntelliAmpEntry 12   }   

            sensorIntelliAmpRearm OBJECT-TYPE
               SYNTAX  INTEGER
               ACCESS  read-write
               STATUS  mandatory
               DESCRIPTION
               "The number of degrees to rearm the status. For example if status goes from normal to warning, the temp must go down iMTempRearm degrees below warning before the status goes to normal"
               ::=  {  sensorIntelliAmpEntry 13   }

            sensorIntelliAmpDelayError OBJECT-TYPE
               SYNTAX  INTEGER (0..65534)
               ACCESS  read-write
               STATUS  mandatory
               DESCRIPTION
               "Time in seconds after the sensor has been in error status before report as an error"
               ::=  {  sensorIntelliAmpEntry 14   }

            sensorIntelliAmpDelayNormal OBJECT-TYPE
               SYNTAX  INTEGER (0..65534)
               ACCESS  read-write
               STATUS  mandatory
               DESCRIPTION
               "Time in seconds after the sensor change from error to normal before report as normal"
               ::=  {  sensorIntelliAmpEntry 15   }

            sensorIntelliAmpDelayLowCritical OBJECT-TYPE
               SYNTAX INTEGER (0..65535)
               ACCESS read-write
               STATUS mandatory
               DESCRIPTION
               "Continuous time for this sensor to be in Low Critical before accepting new Status."
               ::= {  sensorIntelliAmpEntry 16 }
               
            sensorIntelliAmpDelayLowWarning OBJECT-TYPE
               SYNTAX INTEGER (0..65535)
               ACCESS read-write
               STATUS mandatory
               DESCRIPTION
               "Continuous time for this sensor to be in Low Warning before accepting new Status."
               ::= {  sensorIntelliAmpEntry 17 }

            sensorIntelliAmpDelayHighWarning OBJECT-TYPE
               SYNTAX INTEGER (0..65535)
               ACCESS read-write
               STATUS mandatory
               DESCRIPTION
               "Continuous time for this sensor to be in High Warning before accepting new Status."
               ::= {  sensorIntelliAmpEntry 18 }

            sensorIntelliAmpDelayHighCritical OBJECT-TYPE
               SYNTAX INTEGER (0..65535)
               ACCESS read-write
               STATUS mandatory
               DESCRIPTION
               "Continuous time for this sensor to be in High Critical before accepting new Status."
               ::= {  sensorIntelliAmpEntry 19 }

            sensorIntelliAmpRaw OBJECT-TYPE
               SYNTAX  INTEGER 
               ACCESS  read-only
               STATUS  mandatory
               DESCRIPTION
               "The unformatted, raw, A/D value in this sensor. Contains more resolution than the formated percentage. This number can go from 0 to 1023 depending on the input voltage"
               ::=  {  sensorIntelliAmpEntry 20   }

            sensorIntelliAmpOffset OBJECT-TYPE
               SYNTAX  INTEGER
               ACCESS  read-write
               STATUS  mandatory
               DESCRIPTION
               "IntelliAmp Offset reading"
               ::=  {  sensorIntelliAmpEntry 21   }

            sensorIntelliAmpJumper OBJECT-TYPE
               SYNTAX  INTEGER {
                  jumperAt-60(-600),
                  jumperAt-40(-400),
                  jumperAt-30(-300),
                  jumperAt-20(-200),
                  jumperAt-10(-100),
                  jumperAt10(100),
                  jumperAt20(200),
                  jumperAt30(300),
                  jumperAt40(400),                  
                  jumperAt60(600)
               }
               ACCESS  read-write
               STATUS  mandatory
               DESCRIPTION
               "Selected voltage scale (jumper 0) in IntelliAmp conversion."
               ::=  {  sensorIntelliAmpEntry 32   }

            sensorIntelliAmpAmountMaxVoltage OBJECT-TYPE
               SYNTAX  INTEGER
               ACCESS  read-write
               STATUS  mandatory
               DESCRIPTION
               "The maximum scale of IntelliAmp conversion."
               ::=  {  sensorIntelliAmpEntry 33   }

            sensorIntelliAmpAmountBaseVoltage OBJECT-TYPE
               SYNTAX  INTEGER
               ACCESS  read-write
               STATUS  mandatory
               DESCRIPTION
               "The base scale of IntelliAmp conversion."
               ::=  {  sensorIntelliAmpEntry 34   }

            sensorIntelliAmpPort OBJECT-TYPE
               SYNTAX  INTEGER (0..65534)
               ACCESS  read-only
               STATUS  mandatory
               DESCRIPTION
               "Sensor port"
               ::=  {  sensorIntelliAmpEntry 35 }

            sensorIntelliAmpSubPort OBJECT-TYPE
               SYNTAX  INTEGER (0..65534)
               ACCESS  read-only
               STATUS  mandatory
               DESCRIPTION
               "Sensor sub port"
               ::=  {  sensorIntelliAmpEntry 36 }

            sensorIntelliAmpDeviceIndex OBJECT-TYPE
               SYNTAX  INTEGER (0..65534)
               ACCESS  read-only
               STATUS  mandatory
               DESCRIPTION
               "Device Index of sensor"
               ::=  {  sensorIntelliAmpEntry 37 }

            sensorIntelliAmpMaxVoltage OBJECT-TYPE
               SYNTAX  INTEGER
               ACCESS  read-write
               STATUS  mandatory
               DESCRIPTION
               "The max range for use in conversion."
               ::=  {  sensorIntelliAmpEntry 43   }

            sensorIntelliAmpBaseVoltage OBJECT-TYPE
               SYNTAX  INTEGER
               ACCESS  read-write
               STATUS  mandatory
               DESCRIPTION
               "The base range for use in conversion."
               ::=  {  sensorIntelliAmpEntry 44   }

--/* End of sensorIntelliAmpEntry */

--/* Begin of sensorAirflowEntry */
         sensorAirflowTable OBJECT-TYPE
            SYNTAX  SEQUENCE OF SensorAirflowEntry
            ACCESS  not-accessible
            STATUS  mandatory
            DESCRIPTION
            "This table contains the property and reading value for every sensor."
            ::=  {  iMeterSensor 7   }

         sensorAirflowEntry OBJECT-TYPE
            SYNTAX  SensorAirflowEntry
            ACCESS  not-accessible
            STATUS  mandatory
            DESCRIPTION
            "This is an entry in the sensorTemperatureEntry Table"
            INDEX         { sensorAirflowIndex }
            ::=  {  sensorAirflowTable 1 }

         SensorAirflowEntry ::= SEQUENCE {
               sensorAirflowIndex
                  INTEGER,
               sensorAirflowDescription
                  DisplayString,
               sensorAirflowValue
                  INTEGER,
               sensorAirflowStatus
                  INTEGER,
               sensorAirflowGoOffline
                  INTEGER,
               sensorAirflowLowCritical
                  INTEGER,
               sensorAirflowLowWarning
                  INTEGER,
               sensorAirflowHighWarning
                  INTEGER,
               sensorAirflowHighCritical
                  INTEGER,
               sensorAirflowRearm
                  INTEGER,
               sensorAirflowDelayError
                  INTEGER,
               sensorAirflowDelayNormal
                  INTEGER,
               sensorAirflowDelayLowCritical
                  INTEGER,
               sensorAirflowDelayLowWarning
                  INTEGER,
               sensorAirflowDelayHighWarning
                  INTEGER,
               sensorAirflowDelayHighCritical
                  INTEGER,
               sensorAirflowRaw
                  INTEGER,
               sensorAirflowPort
                  INTEGER,
               sensorAirflowSubPort
                  INTEGER,
               sensorAirflowDeviceIndex
                  INTEGER
            }

            sensorAirflowIndex OBJECT-TYPE
               SYNTAX  INTEGER (1..65535)
               ACCESS  read-only
               STATUS  mandatory
               DESCRIPTION
               "The index into the Switch sensor table"
               ::=  {  sensorAirflowEntry 1   }

            sensorAirflowDescription OBJECT-TYPE
               SYNTAX  DisplayString
               ACCESS  read-write
               STATUS  mandatory
               DESCRIPTION
               "A Description of this sensor Switch"
               ::=  {  sensorAirflowEntry 2   }

            sensorAirflowValue OBJECT-TYPE
               SYNTAX  INTEGER
               ACCESS  read-only
               STATUS  mandatory
               DESCRIPTION
               "The reading value in this sensor"
               ::=  {  sensorAirflowEntry 4   }

            sensorAirflowStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorAirflowEntry 6  }

            sensorAirflowGoOffline OBJECT-TYPE
               SYNTAX  INTEGER {
                  online(1),
                  goOffline(2)
               }
               ACCESS  read-write
               STATUS  mandatory
               DESCRIPTION
               "To take offline enter a 2"
               ::=  {  sensorAirflowEntry 8  }

            sensorAirflowLowCritical OBJECT-TYPE
               SYNTAX  INTEGER
               ACCESS  read-write
               STATUS  mandatory
               DESCRIPTION
               "How cold this sensor gets before it sends a critical event"
               ::=  {  sensorAirflowEntry 9   }

            sensorAirflowLowWarning OBJECT-TYPE
               SYNTAX  INTEGER
               ACCESS  read-write
               STATUS  mandatory
               DESCRIPTION
               "How cold this sensor gets before it sends a warning"
               ::=  {  sensorAirflowEntry 10   }
   
            sensorAirflowHighWarning OBJECT-TYPE
               SYNTAX  INTEGER
               ACCESS  read-write
               STATUS  mandatory
               DESCRIPTION
               "How hot this sensor gets before it sends a warning"
               ::=  {  sensorAirflowEntry 11   }  

            sensorAirflowHighCritical OBJECT-TYPE
               SYNTAX  INTEGER
               ACCESS  read-write
               STATUS  mandatory
               DESCRIPTION
               "How hot this sensor gets before it sends a critical event"
               ::=  {  sensorAirflowEntry 12   }   

            sensorAirflowRearm OBJECT-TYPE
               SYNTAX  INTEGER
               ACCESS  read-write
               STATUS  mandatory
               DESCRIPTION
               "The number of degrees to rearm the status. For example if status goes from normal to warning, the temp must go down iMTempRearm degrees below warning before the status goes to normal"
               ::=  {  sensorAirflowEntry 13   }

            sensorAirflowDelayError OBJECT-TYPE
               SYNTAX  INTEGER (0..65534)
               ACCESS  read-write
               STATUS  mandatory
               DESCRIPTION
               "Time in seconds after the sensor has been in error status before report as an error"
               ::=  {  sensorAirflowEntry 14   }

            sensorAirflowDelayNormal OBJECT-TYPE
               SYNTAX  INTEGER (0..65534)
               ACCESS  read-write
               STATUS  mandatory
               DESCRIPTION
               "Time in seconds after the sensor change from error to normal before report as normal"
               ::=  {  sensorAirflowEntry 15   }

            sensorAirflowDelayLowCritical OBJECT-TYPE
               SYNTAX INTEGER (0..65535)
               ACCESS read-write
               STATUS mandatory
               DESCRIPTION
               "Continuous time for this sensor to be in Low Critical before accepting new Status."
               ::= {  sensorAirflowEntry 16 }
               
            sensorAirflowDelayLowWarning OBJECT-TYPE
               SYNTAX INTEGER (0..65535)
               ACCESS read-write
               STATUS mandatory
               DESCRIPTION
               "Continuous time for this sensor to be in Low Warning before accepting new Status."
               ::= {  sensorAirflowEntry 17 }

            sensorAirflowDelayHighWarning OBJECT-TYPE
               SYNTAX INTEGER (0..65535)
               ACCESS read-write
               STATUS mandatory
               DESCRIPTION
               "Continuous time for this sensor to be in High Warning before accepting new Status."
               ::= {  sensorAirflowEntry 18 }

            sensorAirflowDelayHighCritical OBJECT-TYPE
               SYNTAX INTEGER (0..65535)
               ACCESS read-write
               STATUS mandatory
               DESCRIPTION
               "Continuous time for this sensor to be in High Critical before accepting new Status."
               ::= {  sensorAirflowEntry 19 }

            sensorAirflowRaw OBJECT-TYPE
               SYNTAX  INTEGER
               ACCESS  read-only
               STATUS  mandatory
               DESCRIPTION
               "The unformatted, raw, A/D value in this sensor. Contains more resolution than the formated percentage. This number can go from 0 to 1023 depending on the input voltage"
               ::=  {  sensorAirflowEntry 20   }

            sensorAirflowPort OBJECT-TYPE
               SYNTAX  INTEGER (0..65534)
               ACCESS  read-only
               STATUS  mandatory
               DESCRIPTION
               "Sensor port"
               ::=  {  sensorAirflowEntry 35 }

            sensorAirflowSubPort OBJECT-TYPE
               SYNTAX  INTEGER (0..65534)
               ACCESS  read-only
               STATUS  mandatory
               DESCRIPTION
               "Sensor sub port"
               ::=  {  sensorAirflowEntry 36 }

            sensorAirflowDeviceIndex OBJECT-TYPE
               SYNTAX  INTEGER (0..65534)
               ACCESS  read-only
               STATUS  mandatory
               DESCRIPTION
               "Device Index of sensor"
               ::=  {  sensorAirflowEntry 37 }

--/* End of sensorAirflowEntry */

--/* Begin of sensorWaterEntry */
         sensorWaterTable OBJECT-TYPE
            SYNTAX  SEQUENCE OF SensorWaterEntry
            ACCESS  not-accessible
            STATUS  mandatory
            DESCRIPTION
            "This table contains the property and reading value for every sensor."
            ::=  {  iMeterSensor 9   }

         sensorWaterEntry OBJECT-TYPE
            SYNTAX  SensorWaterEntry
            ACCESS  not-accessible
            STATUS  mandatory
            DESCRIPTION
            "This is an entry in the sensorTemperatureEntry Table"
            INDEX         { sensorWaterIndex }
            ::=  {  sensorWaterTable 1 }

         SensorWaterEntry ::= SEQUENCE {
               sensorWaterIndex
                  INTEGER,
               sensorWaterDescription
                  DisplayString,
               sensorWaterStatus
                  INTEGER,
               sensorWaterGoOffline
                  INTEGER,
               sensorWaterPort
                  INTEGER,
               sensorWaterSubPort
                  INTEGER,
               sensorWaterDeviceIndex
                  INTEGER
            }

            sensorWaterIndex OBJECT-TYPE
               SYNTAX  INTEGER (1..65535)
               ACCESS  read-only
               STATUS  mandatory
               DESCRIPTION
               "The index into the Switch sensor table"
               ::=  {  sensorWaterEntry 1   }

            sensorWaterDescription OBJECT-TYPE
               SYNTAX  DisplayString
               ACCESS  read-write
               STATUS  mandatory
               DESCRIPTION
               "A Description of this sensor Switch"
               ::=  {  sensorWaterEntry 2   }

            sensorWaterStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorWaterEntry 6  }

            sensorWaterGoOffline OBJECT-TYPE
               SYNTAX  INTEGER {
                  online(1),
                  goOffline(2)
               }
               ACCESS  read-write
               STATUS  mandatory
               DESCRIPTION
               "To take offline enter a 2"
               ::=  {  sensorWaterEntry 8  }

            sensorWaterPort OBJECT-TYPE
               SYNTAX  INTEGER (0..65534)
               ACCESS  read-only
               STATUS  mandatory
               DESCRIPTION
               "Sensor port"
               ::=  {  sensorWaterEntry 35 }

            sensorWaterSubPort OBJECT-TYPE
               SYNTAX  INTEGER (0..65534)
               ACCESS  read-only
               STATUS  mandatory
               DESCRIPTION
               "Sensor sub port"
               ::=  {  sensorWaterEntry 36 }

            sensorWaterDeviceIndex OBJECT-TYPE
               SYNTAX  INTEGER (0..65534)
               ACCESS  read-only
               STATUS  mandatory
               DESCRIPTION
               "Device Index of sensor"
               ::=  {  sensorWaterEntry 37 }

--/* End of sensorWaterEntry */

--/* Begin of sensorSecurityEntry */
         sensorSecurityTable OBJECT-TYPE
            SYNTAX  SEQUENCE OF SensorSecurityEntry
            ACCESS  not-accessible
            STATUS  mandatory
            DESCRIPTION
            "This table contains the property and reading value for every sensor."
            ::=  {  iMeterSensor 10   }

         sensorSecurityEntry OBJECT-TYPE
            SYNTAX  SensorSecurityEntry
            ACCESS  not-accessible
            STATUS  mandatory
            DESCRIPTION
            "This is an entry in the sensorTemperatureEntry Table"
            INDEX         { sensorSecurityIndex }
            ::=  {  sensorSecurityTable 1 }

         SensorSecurityEntry ::= SEQUENCE {
               sensorSecurityIndex
                  INTEGER,
               sensorSecurityDescription
                  DisplayString,
               sensorSecurityStatus
                  INTEGER,
               sensorSecurityGoOffline
                  INTEGER,
               sensorSecurityPort
                  INTEGER,
               sensorSecuritySubPort
                  INTEGER,
               sensorSecurityDeviceIndex
                  INTEGER
            }

            sensorSecurityIndex OBJECT-TYPE
               SYNTAX  INTEGER (1..65535)
               ACCESS  read-only
               STATUS  mandatory
               DESCRIPTION
               "The index into the Switch sensor table"
               ::=  {  sensorSecurityEntry 1   }

            sensorSecurityDescription OBJECT-TYPE
               SYNTAX  DisplayString
               ACCESS  read-write
               STATUS  mandatory
               DESCRIPTION
               "A Description of this sensor Switch"
               ::=  {  sensorSecurityEntry 2   }

            sensorSecurityStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorSecurityEntry 6  }

            sensorSecurityGoOffline OBJECT-TYPE
               SYNTAX  INTEGER {
                  online(1),
                  goOffline(2)
               }
               ACCESS  read-write
               STATUS  mandatory
               DESCRIPTION
               "To take offline enter a 2"
               ::=  {  sensorSecurityEntry 8  }

            sensorSecurityPort OBJECT-TYPE
               SYNTAX  INTEGER (0..65534)
               ACCESS  read-only
               STATUS  mandatory
               DESCRIPTION
               "Sensor port"
               ::=  {  sensorSecurityEntry 35 }

            sensorSecuritySubPort OBJECT-TYPE
               SYNTAX  INTEGER (0..65534)
               ACCESS  read-only
               STATUS  mandatory
               DESCRIPTION
               "Sensor sub port"
               ::=  {  sensorSecurityEntry 36 }

            sensorSecurityDeviceIndex OBJECT-TYPE
               SYNTAX  INTEGER (0..65534)
               ACCESS  read-only
               STATUS  mandatory
               DESCRIPTION
               "Device Index of sensor"
               ::=  {  sensorSecurityEntry 37 }

--/* End of sensorSecurityEntry */

--/* Begin of sensorSirenEntry */
         sensorSirenTable OBJECT-TYPE
            SYNTAX  SEQUENCE OF SensorSirenEntry
            ACCESS  not-accessible
            STATUS  mandatory
            DESCRIPTION
            "This table contains the property and reading value for every sensor."
            ::=  {  iMeterSensor 11   }

         sensorSirenEntry OBJECT-TYPE
            SYNTAX  SensorSirenEntry
            ACCESS  not-accessible
            STATUS  mandatory
            DESCRIPTION
            "This is an entry in the sensorTemperatureEntry Table"
            INDEX         { sensorSirenIndex }
            ::=  {  sensorSirenTable 1 }

         SensorSirenEntry ::= SEQUENCE {
               sensorSirenIndex
                  INTEGER,
               sensorSirenDescription
                  DisplayString,
               sensorSirenStatus
                  INTEGER,
               sensorSirenGoOffline
                  INTEGER,
               sensorSirenControlMode
                  INTEGER,
               sensorSirenManualCycleTime
                  INTEGER,
               sensorSirenManualAction
                  INTEGER,
               sensorSirenPort
                  INTEGER,
               sensorSirenSubPort
                  INTEGER,
               sensorSirenDeviceIndex
                  INTEGER
            }

            sensorSirenIndex OBJECT-TYPE
               SYNTAX  INTEGER (1..65535)
               ACCESS  read-only
               STATUS  mandatory
               DESCRIPTION
               "The index into the Switch sensor table"
               ::=  {  sensorSirenEntry 1   }

            sensorSirenDescription OBJECT-TYPE
               SYNTAX  DisplayString
               ACCESS  read-write
               STATUS  mandatory
               DESCRIPTION
               "A Description of this sensor Switch"
               ::=  {  sensorSirenEntry 2   }

            sensorSirenStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorSirenEntry 6  }

            sensorSirenGoOffline OBJECT-TYPE
               SYNTAX  INTEGER {
                  online(1),
                  goOffline(2)
               }
               ACCESS  read-write
               STATUS  mandatory
               DESCRIPTION
               "To take offline enter a 2"
               ::=  {  sensorSirenEntry 8  }

            sensorSirenControlMode OBJECT-TYPE
               SYNTAX  INTEGER {
                  manual-control(0),
                  sensor-control(1),
                  time-control(2),
                  thermostat-control(3)
               }
               ACCESS  read-write
               STATUS  mandatory
               DESCRIPTION
               "Control Mode used for selecting the mode to control a siren."
               ::=  {  sensorSirenEntry 24  }
               
            sensorSirenManualCycleTime OBJECT-TYPE
               SYNTAX  INTEGER (1..255)
               ACCESS  read-write
               STATUS  mandatory
               DESCRIPTION
               "Toggle period in seconds for Manual Cycle action."
               ::=  {  sensorSirenEntry 25  }
               
            sensorSirenManualAction OBJECT-TYPE
               SYNTAX  INTEGER {
                  turn-On(0),
                  turn-Off(1),
                  cycle-On-Off-On(2),
                  cycle-Off-On-Off(3)
               }
               ACCESS  read-write
               STATUS  mandatory
               DESCRIPTION
               "Control the siren manualy"
               ::=  {  sensorSirenEntry 26  }

            sensorSirenPort OBJECT-TYPE
               SYNTAX  INTEGER (0..65534)
               ACCESS  read-only
               STATUS  mandatory
               DESCRIPTION
               "Sensor port"
               ::=  {  sensorSirenEntry 35 }

            sensorSirenSubPort OBJECT-TYPE
               SYNTAX  INTEGER (0..65534)
               ACCESS  read-only
               STATUS  mandatory
               DESCRIPTION
               "Sensor sub port"
               ::=  {  sensorSirenEntry 36 }

            sensorSirenDeviceIndex OBJECT-TYPE
               SYNTAX  INTEGER (0..65534)
               ACCESS  read-only
               STATUS  mandatory
               DESCRIPTION
               "Device Index of sensor"
               ::=  {  sensorSirenEntry 37 }

--/* End of sensorSirenEntry */

--/* Begin of sensorRelayEntry */
         sensorRelayTable OBJECT-TYPE
            SYNTAX  SEQUENCE OF SensorRelayEntry
            ACCESS  not-accessible
            STATUS  mandatory
            DESCRIPTION
            "This table contains the property and reading value for every sensor."
            ::=  {  iMeterSensor 12   }

         sensorRelayEntry OBJECT-TYPE
            SYNTAX  SensorRelayEntry
            ACCESS  not-accessible
            STATUS  mandatory
            DESCRIPTION
            "This is an entry in the sensorTemperatureEntry Table"
            INDEX         { sensorRelayIndex }
            ::=  {  sensorRelayTable 1 }

         SensorRelayEntry ::= SEQUENCE {
               sensorRelayIndex
                  INTEGER,
               sensorRelayDescription
                  DisplayString,
               sensorRelayType
                  INTEGER,
               sensorRelayStatus
                  INTEGER,
               sensorRelayGoOffline
                  INTEGER,
               sensorRelayControlMode
                  INTEGER,
               sensorRelayManualCycleTime
                  INTEGER,
               sensorRelayManualAction
                  INTEGER,
               sensorRelayPort
                  INTEGER,
               sensorRelaySubPort
                  INTEGER,
               sensorRelayDeviceIndex
                  INTEGER
            }

            sensorRelayIndex OBJECT-TYPE
               SYNTAX  INTEGER (1..65535)
               ACCESS  read-only
               STATUS  mandatory
               DESCRIPTION
               "The index into the Switch sensor table"
               ::=  {  sensorRelayEntry 1   }

            sensorRelayDescription OBJECT-TYPE
               SYNTAX  DisplayString
               ACCESS  read-write
               STATUS  mandatory
               DESCRIPTION
               "A Description of this sensor Switch"
               ::=  {  sensorRelayEntry 2   }

            sensorRelayType OBJECT-TYPE
               SYNTAX  INTEGER {
                  relay(13)
               }
               ACCESS  read-only
               STATUS  mandatory
               DESCRIPTION
               "Enter the type of this Sensor"
               ::=  {  sensorRelayEntry 3  }

            sensorRelayStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorRelayEntry 6  }

            sensorRelayGoOffline OBJECT-TYPE
               SYNTAX  INTEGER {
                  online(1),
                  goOffline(2)
               }
               ACCESS  read-write
               STATUS  mandatory
               DESCRIPTION
               "To take offline enter a 2"
               ::=  {  sensorRelayEntry 8  }

            sensorRelayControlMode OBJECT-TYPE
               SYNTAX  INTEGER {
                  manual-control(0),
                  sensor-control(1),
                  time-control(2),
                  thermostat-control(3)
               }
               ACCESS  read-write
               STATUS  mandatory
               DESCRIPTION
               "Control Mode used for selecting the mode to control a relay."
               ::=  {  sensorRelayEntry 24  }
               
            sensorRelayManualCycleTime OBJECT-TYPE
               SYNTAX  INTEGER (1..255)
               ACCESS  read-write
               STATUS  mandatory
               DESCRIPTION
               "Toggle period in seconds for Manual Cycle action."
               ::=  {  sensorRelayEntry 25  }
               
            sensorRelayManualAction OBJECT-TYPE
               SYNTAX  INTEGER {
                  turn-On(0),
                  turn-Off(1),
                  cycle-On-Off-On(2),
                  cycle-Off-On-Off(3)
               }
               ACCESS  read-write
               STATUS  mandatory
               DESCRIPTION
               "Control the relay manualy"
               ::=  {  sensorRelayEntry 26  }

            sensorRelayPort OBJECT-TYPE
               SYNTAX  INTEGER (0..65534)
               ACCESS  read-only
               STATUS  mandatory
               DESCRIPTION
               "Sensor port"
               ::=  {  sensorRelayEntry 35 }

            sensorRelaySubPort OBJECT-TYPE
               SYNTAX  INTEGER (0..65534)
               ACCESS  read-only
               STATUS  mandatory
               DESCRIPTION
               "Sensor sub port"
               ::=  {  sensorRelayEntry 36 }

            sensorRelayDeviceIndex OBJECT-TYPE
               SYNTAX  INTEGER (0..65534)
               ACCESS  read-only
               STATUS  mandatory
               DESCRIPTION
               "Device Index of sensor"
               ::=  {  sensorRelayEntry 37 }

--/* End of sensorRelayEntry */

--/* Begin of sensorACvoltageEntry */
         sensorACvoltageTable OBJECT-TYPE
            SYNTAX  SEQUENCE OF SensorACvoltageEntry
            ACCESS  not-accessible
            STATUS  mandatory
            DESCRIPTION
            "This table contains the property and reading value for every sensor."
            ::=  {  iMeterSensor 13   }

         sensorACvoltageEntry OBJECT-TYPE
            SYNTAX  SensorACvoltageEntry
            ACCESS  not-accessible
            STATUS  mandatory
            DESCRIPTION
            "This is an entry in the sensorTemperatureEntry Table"
            INDEX         { sensorACvoltageIndex }
            ::=  {  sensorACvoltageTable 1 }

         SensorACvoltageEntry ::= SEQUENCE {
               sensorACvoltageIndex
                  INTEGER,
               sensorACvoltageDescription
                  DisplayString,
               sensorACvoltageStatus
                  INTEGER,
               sensorACvoltageGoOffline
                  INTEGER,
               sensorACvoltagePort
                  INTEGER,
               sensorACvoltageSubPort
                  INTEGER,
               sensorACvoltageDeviceIndex
                  INTEGER
            }

            sensorACvoltageIndex OBJECT-TYPE
               SYNTAX  INTEGER (1..65535)
               ACCESS  read-only
               STATUS  mandatory
               DESCRIPTION
               "The index into the Switch sensor table"
               ::=  {  sensorACvoltageEntry 1   }

            sensorACvoltageDescription OBJECT-TYPE
               SYNTAX  DisplayString
               ACCESS  read-write
               STATUS  mandatory
               DESCRIPTION
               "A Description of this sensor Switch"
               ::=  {  sensorACvoltageEntry 2   }

            sensorACvoltageStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorACvoltageEntry 6  }

            sensorACvoltageGoOffline OBJECT-TYPE
               SYNTAX  INTEGER {
                  online(1),
                  goOffline(2)
               }
               ACCESS  read-write
               STATUS  mandatory
               DESCRIPTION
               "To put online enter a 1, to take offline enter a 2"
               ::=  {  sensorACvoltageEntry 8  }

            sensorACvoltagePort OBJECT-TYPE
               SYNTAX  INTEGER (0..65534)
               ACCESS  read-only
               STATUS  mandatory
               DESCRIPTION
               "Sensor port"
               ::=  {  sensorACvoltageEntry 35 }

            sensorACvoltageSubPort OBJECT-TYPE
               SYNTAX  INTEGER (0..65534)
               ACCESS  read-only
               STATUS  mandatory
               DESCRIPTION
               "Sensor sub port"
               ::=  {  sensorACvoltageEntry 36 }

            sensorACvoltageDeviceIndex OBJECT-TYPE
               SYNTAX  INTEGER (0..65534)
               ACCESS  read-only
               STATUS  mandatory
               DESCRIPTION
               "Device Index of sensor"
               ::=  {  sensorACvoltageEntry 37 }

--/* End of sensorACvoltageEntry */

--/* Begin of sensorSmokeEntry */
         sensorSmokeTable OBJECT-TYPE
            SYNTAX  SEQUENCE OF SensorSmokeEntry
            ACCESS  not-accessible
            STATUS  mandatory
            DESCRIPTION
            "This table contains the property and reading value for every sensor."
            ::=  {  iMeterSensor 14   }

         sensorSmokeEntry OBJECT-TYPE
            SYNTAX  SensorSmokeEntry
            ACCESS  not-accessible
            STATUS  mandatory
            DESCRIPTION
            "This is an entry in the sensorTemperatureEntry Table"
            INDEX         { sensorSmokeIndex }
            ::=  {  sensorSmokeTable 1 }

         SensorSmokeEntry ::= SEQUENCE {
               sensorSmokeIndex
                  INTEGER,
               sensorSmokeDescription
                  DisplayString,
               sensorSmokeStatus
                  INTEGER,
               sensorSmokeGoOffline
                  INTEGER,
               sensorSmokePort
                  INTEGER,
               sensorSmokeSubPort
                  INTEGER,
               sensorSmokeDeviceIndex
                  INTEGER
            }

            sensorSmokeIndex OBJECT-TYPE
               SYNTAX  INTEGER (1..65535)
               ACCESS  read-only
               STATUS  mandatory
               DESCRIPTION
               "The index into the Switch sensor table"
               ::=  {  sensorSmokeEntry 1   }

            sensorSmokeDescription OBJECT-TYPE
               SYNTAX  DisplayString
               ACCESS  read-write
               STATUS  mandatory
               DESCRIPTION
               "A Description of this sensor Switch"
               ::=  {  sensorSmokeEntry 2   }

            sensorSmokeStatus OBJECT-TYPE
               SYNTAX  INTEGER {
                  noStatus(1),
                  normal(2),
                  highCritical(4),
                  lowCritical(6),
                  sensorError(7),
                  relayOn(8),
                  relayOff(9)
               }
               ACCESS  read-only
               STATUS  mandatory
               DESCRIPTION
               "The current status of this Sensor, only input switches have a status"
               ::=  {  sensorSmokeEntry 6  }

            sensorSmokeGoOffline OBJECT-TYPE
               SYNTAX  INTEGER {
                  online(1),
                  goOffline(2)
               }
               ACCESS  read-write
               STATUS  mandatory
               DESCRIPTION
               "To take offline enter a 2"
               ::=  {  sensorSmokeEntry 8  }

            sensorSmokePort OBJECT-TYPE
               SYNTAX  INTEGER (0..65534)
               ACCESS  read-only
               STATUS  mandatory
               DESCRIPTION
               "Sensor port"
               ::=  {  sensorSmokeEntry 35 }

            sensorSmokeSubPort OBJECT-TYPE
               SYNTAX  INTEGER (0..65534)
               ACCESS  read-only
               STATUS  mandatory
               DESCRIPTION
               "Sensor sub port"
               ::=  {  sensorSmokeEntry 36 }

            sensorSmokeDeviceIndex OBJECT-TYPE
               SYNTAX  INTEGER (0..65534)
               ACCESS  read-only
               STATUS  mandatory
               DESCRIPTION
               "Device Index of sensor"
               ::=  {  sensorSmokeEntry 37 }

--/* End of sensorSmokeEntry */

--/* Begin of sensorThermostatEntry */
         sensorThermostatTable OBJECT-TYPE
            SYNTAX  SEQUENCE OF SensorThermostatEntry
            ACCESS  not-accessible
            STATUS  mandatory
            DESCRIPTION
            "This table contains the property and reading value for every sensor."
            ::=  {  iMeterSensor 20   }

         sensorThermostatEntry OBJECT-TYPE
            SYNTAX  SensorThermostatEntry
            ACCESS  not-accessible
            STATUS  mandatory
            DESCRIPTION
            "This is an entry in the sensorTemperatureEntry Table"
            INDEX         { sensorThermostatIndex }
            ::=  {  sensorThermostatTable 1 }

         SensorThermostatEntry ::= SEQUENCE {
               sensorThermostatIndex
                  INTEGER,
               sensorThermostatDescription
                  DisplayString,
               sensorThermostatDegree
                  INTEGER,
               sensorThermostatStatus
                  INTEGER,
               sensorThermostatGoOffline
                  INTEGER,
               sensorThermostatLowCritical
                  INTEGER,
               sensorThermostatLowWarning
                  INTEGER,
               sensorThermostatHighWarning
                  INTEGER,
               sensorThermostatHighCritical
                  INTEGER,
               sensorThermostatRearm
                  INTEGER,
               sensorThermostatDelayError
                  INTEGER,
               sensorThermostatDelayNormal
                  INTEGER,
               sensorThermostatDelayLowCritical
                  INTEGER,
               sensorThermostatDelayLowWarning
                  INTEGER,
               sensorThermostatDelayHighWarning
                  INTEGER,
               sensorThermostatDelayHighCritical
                  INTEGER,
               sensorThermostatPort
                  INTEGER,
               sensorThermostatSubPort
                  INTEGER,
               sensorThermostatDeviceIndex
                  INTEGER
            }

            sensorThermostatIndex OBJECT-TYPE
               SYNTAX  INTEGER (1..65535)
               ACCESS  read-only
               STATUS  mandatory
               DESCRIPTION
               "The index into the sensor table"
               ::=  {  sensorThermostatEntry 1   }

            sensorThermostatDescription OBJECT-TYPE
               SYNTAX  DisplayString
               ACCESS  read-write
               STATUS  mandatory
               DESCRIPTION
               "A Description of this sensor"
               ::=  {  sensorThermostatEntry 2   }

            sensorThermostatDegree OBJECT-TYPE
               SYNTAX  INTEGER
               ACCESS  read-only
               STATUS  mandatory
               DESCRIPTION
               "The degrees in this sensor"
               ::=  {  sensorThermostatEntry 4   }

            sensorThermostatStatus OBJECT-TYPE
               SYNTAX  INTEGER {
                  noStatus(1),
                  normal(2),
                  highWarning(3),
                  highCritical(4),
                  lowWarning(5),
                  lowCritical(6),
                  sensorError(7)
               }
               ACCESS  read-only
               STATUS  mandatory
               DESCRIPTION
               "The current status of this Sensor"
               ::=  {  sensorThermostatEntry 6   }

            sensorThermostatGoOffline OBJECT-TYPE
               SYNTAX  INTEGER {
                  online(1),
                  goOffline(2)
               }
               ACCESS  read-write
               STATUS  mandatory
               DESCRIPTION
               "To take offline enter a 2"
               ::=  {  sensorThermostatEntry 8   }

            sensorThermostatLowCritical OBJECT-TYPE
               SYNTAX  INTEGER
               ACCESS  read-write
               STATUS  mandatory
               DESCRIPTION
               "How cold this sensor gets before it sends a critical event"
               ::=  {  sensorThermostatEntry 9   }

            sensorThermostatLowWarning OBJECT-TYPE
               SYNTAX  INTEGER
               ACCESS  read-write
               STATUS  mandatory
               DESCRIPTION
               "How cold this sensor gets before it sends a warning"
               ::=  {  sensorThermostatEntry 10   }
   
            sensorThermostatHighWarning OBJECT-TYPE
               SYNTAX  INTEGER
               ACCESS  read-write
               STATUS  mandatory
               DESCRIPTION
               "How hot this sensor gets before it sends a warning"
               ::=  {  sensorThermostatEntry 11   }  

            sensorThermostatHighCritical OBJECT-TYPE
               SYNTAX  INTEGER
               ACCESS  read-write
               STATUS  mandatory
               DESCRIPTION
               "How hot this sensor gets before it sends a critical event"
               ::=  {  sensorThermostatEntry 12   }   

            sensorThermostatRearm OBJECT-TYPE
               SYNTAX  INTEGER
               ACCESS  read-write
               STATUS  mandatory
               DESCRIPTION
               "The number of degrees to rearm the status. For example if status goes from normal to warning, the temp must go down iMTempRearm degrees below warning before the status goes to normal"
               ::=  {  sensorThermostatEntry 13   }

            sensorThermostatDelayError OBJECT-TYPE
               SYNTAX  INTEGER (0..65534)
               ACCESS  read-write
               STATUS  mandatory
               DESCRIPTION
               "Time in seconds after the sensor has been in error status before report as an error"
               ::=  {  sensorThermostatEntry 14   }

            sensorThermostatDelayNormal OBJECT-TYPE
               SYNTAX  INTEGER (0..65534)
               ACCESS  read-write
               STATUS  mandatory
               DESCRIPTION
               "Time in seconds after the sensor change from error to normal before report as normal"
               ::=  {  sensorThermostatEntry 15   }

            sensorThermostatDelayLowCritical OBJECT-TYPE
               SYNTAX INTEGER (0..65535)
               ACCESS read-write
               STATUS mandatory
               DESCRIPTION
               "Continuous time for this sensor to be in Low Critical before accepting new Status."
               ::= {  sensorThermostatEntry 16 }
               
            sensorThermostatDelayLowWarning OBJECT-TYPE
               SYNTAX INTEGER (0..65535)
               ACCESS read-write
               STATUS mandatory
               DESCRIPTION
               "Continuous time for this sensor to be in Low Warning before accepting new Status."
               ::= {  sensorThermostatEntry 17 }

            sensorThermostatDelayHighWarning OBJECT-TYPE
               SYNTAX INTEGER (0..65535)
               ACCESS read-write
               STATUS mandatory
               DESCRIPTION
               "Continuous time for this sensor to be in High Warning before accepting new Status."
               ::= {  sensorThermostatEntry 18 }

            sensorThermostatDelayHighCritical OBJECT-TYPE
               SYNTAX INTEGER (0..65535)
               ACCESS read-write
               STATUS mandatory
               DESCRIPTION
               "Continuous time for this sensor to be in High Critical before accepting new Status."
               ::= {  sensorThermostatEntry 19 }

            sensorThermostatPort OBJECT-TYPE
               SYNTAX  INTEGER (0..65534)
               ACCESS  read-only
               STATUS  mandatory
               DESCRIPTION
               "Sensor port"
               ::=  {  sensorThermostatEntry 35 }

            sensorThermostatSubPort OBJECT-TYPE
               SYNTAX  INTEGER (0..65534)
               ACCESS  read-only
               STATUS  mandatory
               DESCRIPTION
               "Sensor sub port"
               ::=  {  sensorThermostatEntry 36 }

            sensorThermostatDeviceIndex OBJECT-TYPE
               SYNTAX  INTEGER (0..65534)
               ACCESS  read-only
               STATUS  mandatory
               DESCRIPTION
               "Device Index of sensor"
               ::=  {  sensorThermostatEntry 37 }

--/* End of sensorThermostatEntry */

--
-- Varbinds used in TRAP Definitions
--

      iMTraps      OBJECT IDENTIFIER  ::=  {  iM 7   }

      iMSensorStatus OBJECT-TYPE
            SYNTAX  INTEGER {
               noStatus(1),
               normal(2),
               highWarning(3),
               highCritical(4),
               lowWarning(5),
               lowCritical(6),
               sensorError(7),
               turnOn(8),
               turnOff(9)
            }
         ACCESS  read-only
         STATUS  mandatory
         DESCRIPTION
         "The current integer status of the sensor causing this trap to be sent"
         ::=  {  iMTraps 1  }
      
      iMSensorValue OBJECT-TYPE
         SYNTAX  INTEGER
         ACCESS  read-only
         STATUS  mandatory
         DESCRIPTION
         "The current integer value of the sensor causing this trap to be sent"
         ::=  {  iMTraps 2  }
      
      iMSensorLevelExceeded OBJECT-TYPE
         SYNTAX  INTEGER
         ACCESS  read-only
         STATUS  mandatory
         DESCRIPTION
         "The integer level that was exceeded causing this trap to be sent"
         ::=  {  iMTraps 3  }
      

      iMSensorIndex OBJECT-TYPE
         SYNTAX  INTEGER 
         ACCESS  read-only
         STATUS  mandatory
         DESCRIPTION
         "The integer index of the sensor causing this trap to be sent"
         ::=  {  iMTraps 4  }
      

      iMSensorName OBJECT-TYPE
         SYNTAX  DisplayString
         ACCESS  read-only
         STATUS  mandatory
         DESCRIPTION
         "The name of the sensor causing this trap to be sent"
         ::=  {  iMTraps 5  }
      
      iMSensorDescription OBJECT-TYPE
         SYNTAX  DisplayString
         ACCESS  read-only
         STATUS  mandatory
         DESCRIPTION
         "The description of the sensor causing this trap to be sent"
         ::=  {  iMTraps 6  }
      
      iMKeepAlive OBJECT-TYPE
         SYNTAX  INTEGER
         ACCESS  read-only
         STATUS  mandatory
         DESCRIPTION
         "Keep alive trap to be sent"
         ::=  {  iMTraps 7  }
      
      iMType OBJECT-TYPE
         SYNTAX  INTEGER {
            temperature(1),
            intellivolt(2),
            humidity(3),
            water(4),
            intelliamp(5),
            security(6),
            airflow(8),
            siren(9),
            drycontact(10),
            acvoltage(12),
            relay(13),
            motion(14),
            smoke(24),
            virtual(30)
         }
         ACCESS  read-only
         STATUS  mandatory
         DESCRIPTION
         "Type of this sensor"
         ::=  {  iMTraps 8  }
      
      iMSensorStatusName OBJECT-TYPE
         SYNTAX  DisplayString
         ACCESS  read-only
         STATUS  mandatory
         DESCRIPTION
    "The current status of the sensor causing this trap to be sent"
         ::=  {  iMTraps 9  }
      
      iMSensorSubIndex OBJECT-TYPE
         SYNTAX  INTEGER
         ACCESS  read-only
         STATUS  mandatory
         DESCRIPTION
    "The integer sub index of the sensor causing this trap to be sent. Only for temperaturearray and relayarray"
         ::=  {  iMTraps 10  }
      
      iMBoardIndex OBJECT-TYPE
         SYNTAX  INTEGER
         ACCESS  read-only
         STATUS  mandatory
         DESCRIPTION
    "The integer index of the sensor board causing this trap to be sent."
         ::=  {  iMTraps 11  }

      iMBoardDescription OBJECT-TYPE
         SYNTAX  DisplayString
         ACCESS  read-only
         STATUS  mandatory
         DESCRIPTION
    "The description of the sensor board causing this trap to be sent"
         ::=  {  iMTraps 12  }
      
      iMEventTimeStamp OBJECT-TYPE
         SYNTAX  DisplayString
         ACCESS  read-only
         STATUS  mandatory
         DESCRIPTION
    "The time(MM/DD/YYYY HH:MM:SS) of an event causing this trap to be sent"
         ::=  {  iMTraps 13  }
   
      iMEventClassNumber OBJECT-TYPE
         SYNTAX  INTEGER
         ACCESS  read-only
         STATUS  mandatory
         DESCRIPTION
    "The user-defined class number associated with this trap"
         ::=  {  iMTraps 14  }
   
      iMEventClassName OBJECT-TYPE
         SYNTAX  DisplayString
         ACCESS  read-only
         STATUS  mandatory
         DESCRIPTION
    "The user-defined class Name associated with this trap"
         ::=  {  iMTraps 15  }
   
      iMSensorDecimalValue OBJECT-TYPE
         SYNTAX  DisplayString
         ACCESS  read-only
         STATUS  mandatory
         DESCRIPTION
     "The current decimal value of the sensor causing this trap to be sent"
         ::=  {  iMTraps 16  }

      iMSensorAliveHigh OBJECT-TYPE
         SYNTAX  INTEGER
         ACCESS  read-only
         STATUS  mandatory
         DESCRIPTION
         "The highest sensor value in the period"
         ::=  {  iMTraps 17  }

      iMSensorAliveLow OBJECT-TYPE
         SYNTAX  INTEGER
         ACCESS  read-only
         STATUS  mandatory
         DESCRIPTION
         "The  lowset sensor value in the period"
         ::=  {  iMTraps 18  }
         

--                  
-- TRAP Definitions
--
      
   iMNormalStatus TRAP-TYPE
      ENTERPRISE jacarta
      DESCRIPTION
         "iM status is Normal"
      --#TYPE "iM Normal Status"
      --#SEVERITY INFORMATIONAL
      ::= 1

   iMWarningStatus TRAP-TYPE
      ENTERPRISE jacarta
      DESCRIPTION
         "iM status went to Warning"
      --#TYPE "iM Warning Status"
      --#SEVERITY MINOR
      ::= 2

   iMCriticalStatus TRAP-TYPE
      ENTERPRISE jacarta
      DESCRIPTION
         "iM status went to Critical"
      --#TYPE "iM Critical Status"
      --#SEVERITY MAJOR
      ::= 3

   iMDownStatus TRAP-TYPE
      ENTERPRISE jacarta
      DESCRIPTION
         "iM status went to Disabled"
      --#TYPE "iM Down Status"
      --#SEVERITY MINOR
      ::= 4

   iMKeepAliveTrap TRAP-TYPE
      ENTERPRISE jacarta
      DESCRIPTION
         "iM send keep alive trap."
      --#SEVERITY  INFORMATIONAL
      ::= 5
      
   iMUnknownStatus TRAP-TYPE
      ENTERPRISE jacarta
      DESCRIPTION
         "iM status went to Unknown"
      --#TYPE "iM Unknown Status"
      --#SEVERITY INFORMATIONAL
      ::= 7  

-- iMTrapType = generalTypeTrap(2)

   iMTemperatureStatus TRAP-TYPE
      ENTERPRISE jacarta
      VARIABLES
         { iMSensorStatus, iMSensorValue, iMSensorLevelExceeded, 
         iMSensorIndex, iMSensorName, iMSensorDescription }
      DESCRIPTION
         "Temperature sensor trap"
      --#SEVERITY  MAJOR
      ::= 10

   iMAnalogueStatus TRAP-TYPE
      ENTERPRISE jacarta
      VARIABLES
         { iMSensorStatus, iMSensorValue, iMSensorLevelExceeded, 
         iMSensorIndex, iMSensorName, iMSensorDescription }
      DESCRIPTION
         "Analogue Sensor Type"
      --#SEVERITY  MAJOR
      ::= 20

   iMSwitchSensorStatus TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 30

   iMVirtualStatus TRAP-TYPE
      ENTERPRISE jacarta
      VARIABLES
         { iMSensorStatus, iMSensorValue, iMSensorLevelExceeded, 
         iMSensorIndex, iMSensorName, iMSensorDescription }
      DESCRIPTION
         "Virtual sensor trap"
      --#SEVERITY  MAJOR
      ::= 80

-- iMTrapType = statusTypeTraps(4)

   iMSenUnknownStatus TRAP-TYPE
      ENTERPRISE jacarta
      VARIABLES
         { iMSensorStatus, iMSensorValue, iMSensorLevelExceeded, 
         iMSensorIndex, iMSensorName, iMSensorDescription }
      DESCRIPTION
         "iM sensor status went to Unknown"
      --#TYPE "iM Unknown Status"
      --#SUMMARY "%s(%s) Status is now %d on port %d."
      --#ARGUMENTS {4,5,1,3}
      --#SEVERITY MAJOR
      --#TIMEINDEX 4
      ::= 51

   iMSenNormalStatus TRAP-TYPE
      ENTERPRISE jacarta
      VARIABLES
         { iMSensorStatus, iMSensorValue, iMSensorLevelExceeded, 
         iMSensorIndex, iMSensorName, iMSensorDescription }
      DESCRIPTION
         "iM sensor status is Normal"
      --#TYPE "iM Normal Status"
      --#SUMMARY "%s(%s) Status is now %d on port %d."
      --#ARGUMENTS {4,5,1,3}
      --#SEVERITY INFORMATIONAL
      --#TIMEINDEX 4
      ::= 52

   iMSenWarningStatus TRAP-TYPE
      ENTERPRISE jacarta
      VARIABLES
         { iMSensorStatus, iMSensorValue, iMSensorLevelExceeded, 
         iMSensorIndex, iMSensorName, iMSensorDescription }
      DESCRIPTION
         "iM sensor status went to Warning"
      --#TYPE "iM Warning Status"
      --#SUMMARY "%s(%s) Status is now %d on port %d."
      --#ARGUMENTS {4,5,1,3}
      --#SEVERITY MINOR
      --#TIMEINDEX 4
      ::= 53

   iMSenCriticalStatus TRAP-TYPE
      ENTERPRISE jacarta
      VARIABLES
         { iMSensorStatus, iMSensorValue, iMSensorLevelExceeded, 
         iMSensorIndex, iMSensorName, iMSensorDescription }
      DESCRIPTION
         "iM sensor status went to Critical"
      --#TYPE "iM Critical Status"
      --#SUMMARY "%s(%s) Status is now %d on port %d."
      --#ARGUMENTS {4,5,1,3}
      --#SEVERITY MAJOR
      --#TIMEINDEX 4
      ::= 54

   iMSenDownStatus TRAP-TYPE
      ENTERPRISE jacarta
      VARIABLES
         { iMSensorStatus, iMSensorValue, iMSensorLevelExceeded, 
         iMSensorIndex, iMSensorName, iMSensorDescription }
      DESCRIPTION
         "iM sensor status went to Disabled"
      --#TYPE "iM Down Status"
      --#SUMMARY "%s(%s) Status is now %d on port %d."
      --#ARGUMENTS {4,5,1,3}
      --#SEVERITY INFORMATIONAL
      --#TIMEINDEX 4
      ::= 55

-- iMTrapType = iMecificTypeTrap(1)

   iMTemperature1Status TRAP-TYPE
      ENTERPRISE jacarta
      VARIABLES
         { iMSensorStatus, iMSensorValue, iMSensorLevelExceeded, 
         iMSensorIndex, iMSensorName, iMSensorDescription }
      DESCRIPTION
         "Temperature sensor trap"
      --#SEVERITY  MAJOR
      ::= 101

   iMTemperature2Status TRAP-TYPE
      ENTERPRISE jacarta
      VARIABLES
         { iMSensorStatus, iMSensorValue, iMSensorLevelExceeded, 
         iMSensorIndex, iMSensorName, iMSensorDescription }
      DESCRIPTION
         "Temperature sensor trap"
      --#SEVERITY  MAJOR
      ::= 102

   iMTemperature3Status TRAP-TYPE
      ENTERPRISE jacarta
      VARIABLES
         { iMSensorStatus, iMSensorValue, iMSensorLevelExceeded, 
         iMSensorIndex, iMSensorName, iMSensorDescription }
      DESCRIPTION
         "Temperature sensor trap"
      --#SEVERITY  MAJOR
      ::= 103

   iMTemperature4Status TRAP-TYPE
      ENTERPRISE jacarta
      VARIABLES
         { iMSensorStatus, iMSensorValue, iMSensorLevelExceeded, 
         iMSensorIndex, iMSensorName, iMSensorDescription }
      DESCRIPTION
         "Temperature sensor trap"
      --#SEVERITY  MAJOR
      ::= 104

   iMTemperature5Status TRAP-TYPE
      ENTERPRISE jacarta
      VARIABLES
         { iMSensorStatus, iMSensorValue, iMSensorLevelExceeded, 
         iMSensorIndex, iMSensorName, iMSensorDescription }
      DESCRIPTION
         "Temperature sensor trap"
      --#SEVERITY  MAJOR
      ::= 105

   iMTemperature6Status TRAP-TYPE
      ENTERPRISE jacarta
      VARIABLES
         { iMSensorStatus, iMSensorValue, iMSensorLevelExceeded, 
         iMSensorIndex, iMSensorName, iMSensorDescription }
      DESCRIPTION
         "Temperature sensor trap"
      --#SEVERITY  MAJOR
      ::= 106

   iMTemperature7Status TRAP-TYPE
      ENTERPRISE jacarta
      VARIABLES
         { iMSensorStatus, iMSensorValue, iMSensorLevelExceeded, 
         iMSensorIndex, iMSensorName, iMSensorDescription }
      DESCRIPTION
         "Temperature sensor trap"
      --#SEVERITY  MAJOR
      ::= 107

   iMTemperature8Status TRAP-TYPE
      ENTERPRISE jacarta
      VARIABLES
         { iMSensorStatus, iMSensorValue, iMSensorLevelExceeded, 
         iMSensorIndex, iMSensorName, iMSensorDescription }
      DESCRIPTION
         "Temperature sensor trap"
      --#SEVERITY  MAJOR
      ::= 108

   iMAnalogue1Status TRAP-TYPE
      ENTERPRISE jacarta
      VARIABLES
         { iMSensorStatus, iMSensorValue, iMSensorLevelExceeded, 
         iMSensorIndex, iMSensorName, iMSensorDescription }
      DESCRIPTION
         "Analogue Sensor Type"
      --#SEVERITY  MAJOR
      ::= 201

   iMAnalogue2Status TRAP-TYPE
      ENTERPRISE jacarta
      VARIABLES
         { iMSensorStatus, iMSensorValue, iMSensorLevelExceeded, 
         iMSensorIndex, iMSensorName, iMSensorDescription }
      DESCRIPTION
         "Analogue Sensor Type"
      --#SEVERITY  MAJOR
      ::= 202

   iMAnalogue3Status TRAP-TYPE
      ENTERPRISE jacarta
      VARIABLES
         { iMSensorStatus, iMSensorValue, iMSensorLevelExceeded, 
         iMSensorIndex, iMSensorName, iMSensorDescription }
      DESCRIPTION
         "Analogue Sensor Type"
      --#SEVERITY  MAJOR
      ::= 203

   iMAnalogue4Status TRAP-TYPE
      ENTERPRISE jacarta
      VARIABLES
         { iMSensorStatus, iMSensorValue, iMSensorLevelExceeded, 
         iMSensorIndex, iMSensorName, iMSensorDescription }
      DESCRIPTION
         "Analogue Sensor Type"
      --#SEVERITY  MAJOR
      ::= 204

   iMAnalogue5Status TRAP-TYPE
      ENTERPRISE jacarta
      VARIABLES
         { iMSensorStatus, iMSensorValue, iMSensorLevelExceeded, 
         iMSensorIndex, iMSensorName, iMSensorDescription }
      DESCRIPTION
         "Analogue Sensor Type"
      --#SEVERITY  MAJOR
      ::= 205

   iMAnalogue6Status TRAP-TYPE
      ENTERPRISE jacarta
      VARIABLES
         { iMSensorStatus, iMSensorValue, iMSensorLevelExceeded, 
         iMSensorIndex, iMSensorName, iMSensorDescription }
      DESCRIPTION
         "Analogue Sensor Type"
      --#SEVERITY  MAJOR
      ::= 206

   iMAnalogue7Status TRAP-TYPE
      ENTERPRISE jacarta
      VARIABLES
         { iMSensorStatus, iMSensorValue, iMSensorLevelExceeded, 
         iMSensorIndex, iMSensorName, iMSensorDescription }
      DESCRIPTION
         "Analogue Sensor Type"
      --#SEVERITY  MAJOR
      ::= 207

   iMAnalogue8Status TRAP-TYPE
      ENTERPRISE jacarta
      VARIABLES
         { iMSensorStatus, iMSensorValue, iMSensorLevelExceeded, 
         iMSensorIndex, iMSensorName, iMSensorDescription }
      DESCRIPTION
         "Analogue Sensor Type"
      --#SEVERITY  MAJOR
      ::= 208



   iMSwitch1Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 301

   iMSwitch2Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 302

   iMSwitch3Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 303

   iMSwitch4Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 304

   iMSwitch5Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 305

   iMSwitch6Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 306

   iMSwitch7Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 307

   iMSwitch8Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 308

   iMSwitch9Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 309

   iMSwitch10Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 310

   iMSwitch11Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 311

   iMSwitch12Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 312

   iMSwitch13Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 313

   iMSwitch14Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 314

   iMSwitch15Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 315

   iMSwitch16Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 316

   iMSwitch17Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 317

   iMSwitch18Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 318

   iMSwitch19Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 319

   iMSwitch20Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 320

   iMSwitch21Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 321

   iMSwitch22Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 322

   iMSwitch23Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 323

   iMSwitch24Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 324

   iMSwitch25Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 325

   iMSwitch26Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 326

   iMSwitch27Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 327

   iMSwitch28Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 328

   iMSwitch29Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 329

   iMSwitch30Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 330

   iMSwitch31Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 331

   iMSwitch32Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 332

   iMSwitch33Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 333

   iMSwitch34Status TRAP-TYPE
      ENTERPRISE jacarta
      VARIABLES
         { iMSensorStatus, iMSensorValue, iMSensorLevelExceeded, 
         iMSensorIndex, iMSensorName, iMSensorDescription }
      DESCRIPTION
         "Switch sensor trap"
      --#SEVERITY  MAJOR
      ::= 334

   iMSwitch35Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 335

   iMSwitch36Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 336

   iMSwitch37Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 337

   iMSwitch38Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 338

   iMSwitch39Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 339

   iMSwitch40Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 340

   iMSwitch41Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 341

   iMSwitch42Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 342

   iMSwitch43Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 343

   iMSwitch44Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 344

   iMSwitch45Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 345

   iMSwitch46Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 346

   iMSwitch47Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 347

   iMSwitch48Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 348

   iMSwitch49Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 349

   iMSwitch50Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 350

   iMSwitch51Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 351

   iMSwitch52Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 352

   iMSwitch53Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 353

   iMSwitch54Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 354

   iMSwitch55Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 355

   iMSwitch56Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 356

   iMSwitch57Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 357

   iMSwitch58Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 358

   iMSwitch59Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 359

   iMSwitch60Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 360

   iMSwitch61Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 361

   iMSwitch62Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 362

   iMSwitch63Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 363

   iMSwitch64Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 364

   iMSwitch65Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 365

   iMSwitch66Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 366

   iMSwitch67Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 367

   iMSwitch68Status TRAP-TYPE
      ENTERPRISE jacarta
      VARIABLES
         { iMSensorStatus, iMSensorValue, iMSensorLevelExceeded,
         iMSensorIndex, iMSensorName, iMSensorDescription }
      DESCRIPTION
         "Switch sensor trap"
      --#SEVERITY  MAJOR
      ::= 368

   iMVirtual1Status TRAP-TYPE
      ENTERPRISE jacarta
      VARIABLES
         { iMSensorStatus, iMSensorValue, iMSensorLevelExceeded, 
         iMSensorIndex, iMSensorName, iMSensorDescription }
      DESCRIPTION
         "Virtual1 sensor trap"
      --#SEVERITY  MAJOR
      ::= 801

   iMVirtual2Status TRAP-TYPE
      ENTERPRISE jacarta
      VARIABLES
         { iMSensorStatus, iMSensorValue, iMSensorLevelExceeded, 
         iMSensorIndex, iMSensorName, iMSensorDescription }
      DESCRIPTION
         "Virtual2 sensor trap"
      --#SEVERITY  MAJOR
      ::= 802

   iMVirtual3Status TRAP-TYPE
      ENTERPRISE jacarta
      VARIABLES
         { iMSensorStatus, iMSensorValue, iMSensorLevelExceeded, 
         iMSensorIndex, iMSensorName, iMSensorDescription }
      DESCRIPTION
         "Virtual3 sensor trap"
      --#SEVERITY  MAJOR
      ::= 803

   iMVirtual4Status TRAP-TYPE
      ENTERPRISE jacarta
      VARIABLES
         { iMSensorStatus, iMSensorValue, iMSensorLevelExceeded, 
         iMSensorIndex, iMSensorName, iMSensorDescription }
      DESCRIPTION
         "Virtual4 sensor trap"
      --#SEVERITY  MAJOR
      ::= 804

   iMVirtual5Status TRAP-TYPE
      ENTERPRISE jacarta
      VARIABLES
         { iMSensorStatus, iMSensorValue, iMSensorLevelExceeded, 
         iMSensorIndex, iMSensorName, iMSensorDescription }
      DESCRIPTION
         "Virtual5 sensor trap"
      --#SEVERITY  MAJOR
      ::= 805

   iMVirtual6Status TRAP-TYPE
      ENTERPRISE jacarta
      VARIABLES
         { iMSensorStatus, iMSensorValue, iMSensorLevelExceeded, 
         iMSensorIndex, iMSensorName, iMSensorDescription }
      DESCRIPTION
         "Virtual6 sensor trap"
      --#SEVERITY  MAJOR
      ::= 806

   iMVirtual7Status TRAP-TYPE
      ENTERPRISE jacarta
      VARIABLES
         { iMSensorStatus, iMSensorValue, iMSensorLevelExceeded, 
         iMSensorIndex, iMSensorName, iMSensorDescription }
      DESCRIPTION
         "Virtual7 sensor trap"
      --#SEVERITY  MAJOR
      ::= 807

   iMVirtual8Status TRAP-TYPE
      ENTERPRISE jacarta
      VARIABLES
         { iMSensorStatus, iMSensorValue, iMSensorLevelExceeded, 
         iMSensorIndex, iMSensorName, iMSensorDescription }
      DESCRIPTION
         "Virtual8 sensor trap"
      --#SEVERITY  MAJOR
      ::= 808

   iMVirtual9Status TRAP-TYPE
      ENTERPRISE jacarta
      VARIABLES
         { iMSensorStatus, iMSensorValue, iMSensorLevelExceeded, 
         iMSensorIndex, iMSensorName, iMSensorDescription }
      DESCRIPTION
         "Virtual9 sensor trap"
      --#SEVERITY  MAJOR
      ::= 809

   iMVirtual10Status TRAP-TYPE
      ENTERPRISE jacarta
      VARIABLES
         { iMSensorStatus, iMSensorValue, iMSensorLevelExceeded, 
         iMSensorIndex, iMSensorName, iMSensorDescription }
      DESCRIPTION
         "Virtual10 sensor trap"
      --#SEVERITY  MAJOR
      ::= 810

   iMVirtual11Status TRAP-TYPE
      ENTERPRISE jacarta
      VARIABLES
         { iMSensorStatus, iMSensorValue, iMSensorLevelExceeded, 
         iMSensorIndex, iMSensorName, iMSensorDescription }
      DESCRIPTION
         "Virtual11 sensor trap"
      --#SEVERITY  MAJOR
      ::= 811

   iMVirtual12Status TRAP-TYPE
      ENTERPRISE jacarta
      VARIABLES
         { iMSensorStatus, iMSensorValue, iMSensorLevelExceeded, 
         iMSensorIndex, iMSensorName, iMSensorDescription }
      DESCRIPTION
         "Virtual12 sensor trap"
      --#SEVERITY  MAJOR
      ::= 812

   iMVirtual13Status TRAP-TYPE
      ENTERPRISE jacarta
      VARIABLES
         { iMSensorStatus, iMSensorValue, iMSensorLevelExceeded, 
         iMSensorIndex, iMSensorName, iMSensorDescription }
      DESCRIPTION
         "Virtual13 sensor trap"
      --#SEVERITY  MAJOR
      ::= 813

   iMVirtual14Status TRAP-TYPE
      ENTERPRISE jacarta
      VARIABLES
         { iMSensorStatus, iMSensorValue, iMSensorLevelExceeded, 
         iMSensorIndex, iMSensorName, iMSensorDescription }
      DESCRIPTION
         "Virtual14 sensor trap"
      --#SEVERITY  MAJOR
      ::= 814

   iMVirtual15Status TRAP-TYPE
      ENTERPRISE jacarta
      VARIABLES
         { iMSensorStatus, iMSensorValue, iMSensorLevelExceeded, 
         iMSensorIndex, iMSensorName, iMSensorDescription }
      DESCRIPTION
         "Virtual15 sensor trap"
      --#SEVERITY  MAJOR
      ::= 815

   iMVirtual16Status TRAP-TYPE
      ENTERPRISE jacarta
      VARIABLES
         { iMSensorStatus, iMSensorValue, iMSensorLevelExceeded, 
         iMSensorIndex, iMSensorName, iMSensorDescription }
      DESCRIPTION
         "Virtual16 sensor trap"
      --#SEVERITY  MAJOR
      ::= 816

   iMVirtual17Status TRAP-TYPE
      ENTERPRISE jacarta
      VARIABLES
         { iMSensorStatus, iMSensorValue, iMSensorLevelExceeded, 
         iMSensorIndex, iMSensorName, iMSensorDescription }
      DESCRIPTION
         "Virtual17 sensor trap"
      --#SEVERITY  MAJOR
      ::= 817

   iMVirtual18Status TRAP-TYPE
      ENTERPRISE jacarta
      VARIABLES
         { iMSensorStatus, iMSensorValue, iMSensorLevelExceeded, 
         iMSensorIndex, iMSensorName, iMSensorDescription }
      DESCRIPTION
         "Virtual18 sensor trap"
      --#SEVERITY  MAJOR
      ::= 818

   iMVirtual19Status TRAP-TYPE
      ENTERPRISE jacarta
      VARIABLES
         { iMSensorStatus, iMSensorValue, iMSensorLevelExceeded, 
         iMSensorIndex, iMSensorName, iMSensorDescription }
      DESCRIPTION
         "Virtual19 sensor trap"
      --#SEVERITY  MAJOR
      ::= 819

   iMVirtual20Status TRAP-TYPE
      ENTERPRISE jacarta
      VARIABLES
         { iMSensorStatus, iMSensorValue, iMSensorLevelExceeded, 
         iMSensorIndex, iMSensorName, iMSensorDescription }
      DESCRIPTION
         "Virtual20 sensor trap"
      --#SEVERITY  MAJOR
      ::= 820

   iMCustomStatus TRAP-TYPE
      ENTERPRISE jacarta
      VARIABLES
         { iMSensorStatus, iMSensorValue, iMSensorLevelExceeded, 
         iMSensorIndex, iMSensorName, iMSensorDescription,
    iMType, iMSensorStatusName, iMSensorSubIndex,
    iMBoardIndex, iMBoardDescription, iMEventTimeStamp,
    iMEventClassNumber, iMEventClassName }
      DESCRIPTION
         "Custom sensor trap"
      --#SEVERITY  MAJOR
      ::= 1000
               
END
